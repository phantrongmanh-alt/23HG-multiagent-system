;;; =====================================================================
;;; 23HG CAD - AutoLISP SINH TU DONG tu DrawingPlan (tools/cad_drafting/render_lisp.py)
;;; Du an: NHA O MAU (DU LIEU MINH HOA)
;;; Ban ve: MAT BANG TANG 1 KT-01
;;; Ty le 1:100 - don vi mm - so lenh ve: 343
;;; CHUA chay thu tren AutoCAD trong CI - chi kiem tra cu phap tinh
;;; (ngoac can bang, chuoi dong du, escape hop le, thuan ASCII).
;;; Chu tieng Viet ghi dang \U+XXXX vi AutoLISP doc file theo bang ma ANSI.
;;; Cach dung: APPLOAD file nay roi go lenh 23HG_VE. Moi doi tuong mang XDATA 23HG_CAD (eid, skill).
;;; =====================================================================
(vl-load-com)

;;; Dem doi tuong da tao / loi, polyline tam cua hatch
(setq hg23:n 0 hg23:nloi 0 hg23:tmp nil)

(defun hg23:em (eid lst / r)
  ;; entmake mot doi tuong; that bai thi dem loi va in ra (khong bo im lang)
  (setq r (entmake lst))
  (if r
    (setq hg23:n (1+ hg23:n))
    (progn
      (setq hg23:nloi (1+ hg23:nloi))
      (princ (strcat "\n23HG: khong tao duoc " eid))))
  r)

(defun hg23:xd (en eid skill)
  ;; gan XDATA 23HG_CAD cho doi tuong tao bang ActiveX
  (if en
    (entmod (append (entget en)
                    (list (list -3 (list "23HG_CAD" (cons 1000 eid) (cons 1000 skill))))))))

(defun hg23:ltype (name)
  ;; nap kieu duong tu acadiso.lin neu ban ve chua co
  (if (and name (/= (strcase name) "CONTINUOUS") (not (tblsearch "LTYPE" name)))
    (vl-catch-all-apply 'vla-load (list (vla-get-Linetypes hg23:doc) name "acadiso.lin")))
  (tblsearch "LTYPE" name))

(defun hg23:layer (name color ltype lw plot desc / lay)
  (setq lay (vla-add (vla-get-Layers hg23:doc) name))
  (vl-catch-all-apply 'vla-put-Color (list lay color))
  (if (hg23:ltype ltype)
    (vla-put-Linetype lay ltype)
    (princ (strcat "\n23HG: khong nap duoc kieu duong " ltype " - layer " name " dung Continuous")))
  (vl-catch-all-apply 'vla-put-Lineweight (list lay lw))
  (vla-put-Plottable lay (if plot :vlax-true :vlax-false))
  ;; layer da co trong ban ve dich co the dang tat / dong bang / khoa: bat lai de doi tuong tao ra nhin thay, sua duoc
  (vl-catch-all-apply 'vla-put-LayerOn (list lay :vlax-true))
  (vl-catch-all-apply 'vla-put-Freeze (list lay :vlax-false))
  (vl-catch-all-apply 'vla-put-Lock (list lay :vlax-false))
  (if (/= desc "") (vl-catch-all-apply 'vla-put-Description (list lay desc)))
  lay)

(defun hg23:style (name font / st)
  (setq st (vla-add (vla-get-TextStyles hg23:doc) name))
  (if (vl-catch-all-error-p (vl-catch-all-apply 'vla-put-FontFile (list st font)))
    (princ (strcat "\n23HG: khong dat duoc font " font " cho kieu chu " name)))
  ;; kieu chu co chieu cao co dinh se lam kich thuoc bo qua DIMTXT: dat chieu cao 0, he so rong 1
  (vl-catch-all-apply 'vla-put-Height (list st 0.0))
  (vl-catch-all-apply 'vla-put-Width (list st 1.0))
  st)

(defun hg23:dimstyle (name vars)
  ;; dat bien DIM* bang setvar roi luu thanh dimstyle (da co thi ghi de)
  (foreach v vars
    (if (vl-catch-all-error-p (vl-catch-all-apply 'setvar (list (car v) (cdr v))))
      (princ (strcat "\n23HG: khong dat duoc bien " (car v) " cho dimstyle " name))))
  (if (tblsearch "DIMSTYLE" name)
    (command "_.-DIMSTYLE" "_Save" name "_Y")
    (command "_.-DIMSTYLE" "_Save" name))
  (princ))

(defun hg23:props (o color ltype lw)
  (if color (vla-put-Color o color))
  (if (and ltype (hg23:ltype ltype)) (vla-put-Linetype o ltype))
  (if lw (vla-put-Lineweight o lw)))

(defun hg23:pl (lay pts / o)
  ;; polyline kin tam lam bien hatch
  (entmake (append (list '(0 . "LWPOLYLINE") '(100 . "AcDbEntity") (cons 8 lay) '(100 . "AcDbPolyline")
                         (cons 90 (length pts)) '(70 . 1))
                   (mapcar '(lambda (p) (cons 10 p)) pts)))
  (setq o (vlax-ename->vla-object (entlast)))
  (setq hg23:tmp (cons o hg23:tmp))
  o)

(defun hg23:objarr (objs / sa)
  (setq sa (vlax-make-safearray vlax-vbObject (cons 0 (1- (length objs)))))
  (vlax-safearray-fill sa objs))

(defun hg23:xoa-tam ()
  ;; xoa polyline tam (ke ca khi hatch loi giua chung)
  (foreach o hg23:tmp (vl-catch-all-apply 'vla-Delete (list o)))
  (setq hg23:tmp nil))

(defun hg23:hatch1 (eid skill lay pat scl ang color ltype lw loops / h)
  (setq h (vla-AddHatch hg23:ms acHatchPatternTypePreDefined pat :vlax-false))
  (setq hg23:tmp (cons h hg23:tmp))
  (vla-put-Layer h lay)
  (hg23:props h color ltype lw)
  (if (/= (strcase pat) "SOLID")
    (progn (vla-put-PatternScale h scl) (vla-put-PatternAngle h ang)))
  (vla-AppendOuterLoop h (hg23:objarr (list (hg23:pl lay (car loops)))))
  (foreach lp (cdr loops)
    (vla-AppendInnerLoop h (hg23:objarr (list (hg23:pl lay lp)))))
  (vla-Evaluate h)
  (setq hg23:tmp (vl-remove h hg23:tmp))
  (hg23:xd (vlax-vla-object->ename h) eid skill)
  h)

(defun hg23:dim1 (eid skill lay style p1 p2 base ang txt color ltype lw / d)
  (setq d (vla-AddDimRotated hg23:ms (vlax-3d-point p1) (vlax-3d-point p2) (vlax-3d-point base) ang))
  (vla-put-Layer d lay)
  (if (tblsearch "DIMSTYLE" style)
    (vla-put-StyleName d style)
    (princ (strcat "\n23HG: chua co dimstyle " style " - kich thuoc " eid " dung kieu hien hanh")))
  (if txt (vla-put-TextOverride d txt))
  (hg23:props d color ltype lw)
  (hg23:xd (vlax-vla-object->ename d) eid skill)
  d)

(defun hg23:try (eid fn args / r)
  ;; goi ham tao doi tuong ActiveX; loi thi dem, in ra va don polyline tam
  (setq r (vl-catch-all-apply fn args))
  (hg23:xoa-tam)
  (if (or (null r) (vl-catch-all-error-p r))
    (progn
      (setq hg23:nloi (1+ hg23:nloi))
      (princ (strcat "\n23HG: khong tao duoc " eid
                     (if (vl-catch-all-error-p r) (strcat " - " (vl-catch-all-error-message r)) ""))))
    (setq hg23:n (1+ hg23:n)))
  r)

(defun hg23:bang ()
  ;; layer, kieu chu, kieu kich thuoc, block
  (hg23:layer "00-ANH-NEN" 8 "Continuous" 9 nil "\U+1EA2nh/PDF n\U+1EC1n tham chi\U+1EBFu (kh\U+00F4ng in)") ; anh_nen
  (hg23:layer "KT-TRUC" 1 "CENTER" 18 T "\U+0110\U+01B0\U+1EDDng tr\U+1EE5c \U+0111\U+1ECBnh v\U+1ECB") ; truc
  (hg23:layer "KT-TRUC-KH" 1 "Continuous" 18 T "V\U+00F2ng tr\U+00F2n v\U+00E0 t\U+00EAn tr\U+1EE5c") ; truc_kh
  (hg23:layer "KC-COT" 7 "Continuous" 50 T "\U+0110\U+01B0\U+1EDDng bao c\U+1ED9t") ; cot
  (hg23:layer "KT-TUONG" 7 "Continuous" 50 T "\U+0110\U+01B0\U+1EDDng bao t\U+01B0\U+1EDDng (\U+0111\U+00E3 tr\U+1EEB \U+00F4 c\U+1EEDa, c\U+1ED9t)") ; tuong
  (hg23:layer "KT-CUA" 3 "Continuous" 25 T "C\U+00E1nh c\U+1EEDa, cung m\U+1EDF, khung c\U+1EEDa s\U+1ED5") ; cua
  (hg23:layer "KT-CUA-KH" 3 "Continuous" 18 T "K\U+00FD hi\U+1EC7u c\U+1EEDa D1/S1") ; cua_kh
  (hg23:layer "KT-THANG" 6 "Continuous" 25 T "C\U+1EA7u thang: b\U+1EADc, m\U+0169i t\U+00EAn, \U+0111\U+01B0\U+1EDDng c\U+1EAFt") ; thang
  (hg23:layer "KT-NOI-THAT" 8 "Continuous" 13 T "N\U+1ED9i th\U+1EA5t, thi\U+1EBFt b\U+1ECB v\U+1EC7 sinh") ; noi_that
  (hg23:layer "KT-HATCH" 8 "Continuous" 9 T "Hatch c\U+1ED9t, t\U+01B0\U+1EDDng, s\U+00E0n") ; hatch
  (hg23:layer "KT-DIM" 3 "Continuous" 18 T "K\U+00EDch th\U+01B0\U+1EDBc (DIMENSION nguy\U+00EAn b\U+1EA3n)") ; dim
  (hg23:layer "KT-HOAN-THIEN" 2 "Continuous" 18 T "T\U+00EAn ph\U+00F2ng, di\U+1EC7n t\U+00EDch, cote, ho\U+00E0n thi\U+1EC7n") ; hoan_thien
  (hg23:layer "KT-KHUNG-TEN" 7 "Continuous" 35 T "Khung t\U+00EAn, khung b\U+1EA3n v\U+1EBD") ; khung_ten
  (hg23:layer "KT-KIEM-TRA" 1 "Continuous" 25 nil "\U+0110\U+00E1nh d\U+1EA5u l\U+1ED7i c\U+1EE7a Validator (kh\U+00F4ng in)") ; kiem_tra
  (hg23:style "VN_ARIAL" "arial.ttf")
  (hg23:dimstyle "TCVN_KT_100" '(("DIMBLK" . "_ARCHTICK") ("DIMTAD" . 1) ("DIMEXO" . 2.0) ("DIMEXE" . 1.5) ("DIMTXT" . 2.2) ("DIMASZ" . 1.5) ("DIMGAP" . 0.8) ("DIMDEC" . 0) ("DIMLUNIT" . 2) ("DIMZIN" . 8) ("DIMTIH" . 0) ("DIMTOH" . 0) ("DIMTXSTY" . "VN_ARIAL") ("DIMCLRD" . 3) ("DIMCLRE" . 3) ("DIMCLRT" . 7) ("DIMSCALE" . 100.0) ("DIMLFAC" . 1.0) ("DIMRND" . 0.0) ("DIMALT" . 0) ("DIMSE1" . 0) ("DIMSE2" . 0) ("DIMTSZ" . 0.0) ("DIMSAH" . 0) ("DIMDLE" . 0.0) ("DIMTFAC" . 1.0) ("DIMTVP" . 0.0) ("DIMJUST" . 0)))
  (if (not (tblsearch "BLOCK" "GIUONG_DOI"))
    (progn
      (entmake '((0 . "BLOCK") (2 . "GIUONG_DOI") (70 . 0) (10 0.0 0.0 0.0)))
      (entmake '((0 . "LWPOLYLINE") (100 . "AcDbEntity") (8 . "0") (100 . "AcDbPolyline") (90 . 4) (70 . 1) (10 0.0 0.0) (10 1600.0 0.0) (10 1600.0 2000.0) (10 0.0 2000.0)))
      (entmake '((0 . "LINE") (8 . "0") (10 0.0 1920.0 0.0) (11 1600.0 1920.0 0.0)))
      (entmake '((0 . "LWPOLYLINE") (100 . "AcDbEntity") (8 . "0") (100 . "AcDbPolyline") (90 . 8) (70 . 1) (10 170.0 1530.0) (10 710.0 1530.0) (10 760.0 1580.0) (10 760.0 1830.0) (10 710.0 1880.0) (10 170.0 1880.0) (10 120.0 1830.0) (10 120.0 1580.0)))
      (entmake '((0 . "LWPOLYLINE") (100 . "AcDbEntity") (8 . "0") (100 . "AcDbPolyline") (90 . 8) (70 . 1) (10 890.0 1530.0) (10 1430.0 1530.0) (10 1480.0 1580.0) (10 1480.0 1830.0) (10 1430.0 1880.0) (10 890.0 1880.0) (10 840.0 1830.0) (10 840.0 1580.0)))
      (entmake '((0 . "LINE") (8 . "0") (10 0.0 1400.0 0.0) (11 1600.0 1400.0 0.0)))
      (entmake '((0 . "LINE") (8 . "0") (10 1150.0 1400.0 0.0) (11 1600.0 950.0 0.0)))
      (entmake '((0 . "ENDBLK"))))
    (princ (strcat "\n23HG: block " "GIUONG_DOI" " da co trong ban ve - giu dinh nghia cu")))
  (if (not (tblsearch "BLOCK" "TU_AO"))
    (progn
      (entmake '((0 . "BLOCK") (2 . "TU_AO") (70 . 0) (10 0.0 0.0 0.0)))
      (entmake '((0 . "LWPOLYLINE") (100 . "AcDbEntity") (8 . "0") (100 . "AcDbPolyline") (90 . 4) (70 . 1) (10 0.0 0.0) (10 1200.0 0.0) (10 1200.0 600.0) (10 0.0 600.0)))
      (entmake '((0 . "LINE") (8 . "0") (10 60.0 300.0 0.0) (11 1140.0 300.0 0.0)))
      (entmake '((0 . "LINE") (8 . "0") (10 140.0 120.0 0.0) (11 220.0 480.0 0.0)))
      (entmake '((0 . "LINE") (8 . "0") (10 280.0 120.0 0.0) (11 360.0 480.0 0.0)))
      (entmake '((0 . "LINE") (8 . "0") (10 420.0 120.0 0.0) (11 500.0 480.0 0.0)))
      (entmake '((0 . "LINE") (8 . "0") (10 560.0 120.0 0.0) (11 640.0 480.0 0.0)))
      (entmake '((0 . "LINE") (8 . "0") (10 700.0 120.0 0.0) (11 780.0 480.0 0.0)))
      (entmake '((0 . "LINE") (8 . "0") (10 840.0 120.0 0.0) (11 920.0 480.0 0.0)))
      (entmake '((0 . "LINE") (8 . "0") (10 980.0 120.0 0.0) (11 1060.0 480.0 0.0)))
      (entmake '((0 . "ENDBLK"))))
    (princ (strcat "\n23HG: block " "TU_AO" " da co trong ban ve - giu dinh nghia cu")))
  (if (not (tblsearch "BLOCK" "SOFA_3"))
    (progn
      (entmake '((0 . "BLOCK") (2 . "SOFA_3") (70 . 0) (10 0.0 0.0 0.0)))
      (entmake '((0 . "LWPOLYLINE") (100 . "AcDbEntity") (8 . "0") (100 . "AcDbPolyline") (90 . 4) (70 . 1) (10 0.0 0.0) (10 2100.0 0.0) (10 2100.0 850.0) (10 0.0 850.0)))
      (entmake '((0 . "LINE") (8 . "0") (10 150.0 0.0 0.0) (11 150.0 850.0 0.0)))
      (entmake '((0 . "LINE") (8 . "0") (10 1950.0 0.0 0.0) (11 1950.0 850.0 0.0)))
      (entmake '((0 . "LINE") (8 . "0") (10 150.0 650.0 0.0) (11 1950.0 650.0 0.0)))
      (entmake '((0 . "LINE") (8 . "0") (10 750.0 0.0 0.0) (11 750.0 650.0 0.0)))
      (entmake '((0 . "LINE") (8 . "0") (10 1350.0 0.0 0.0) (11 1350.0 650.0 0.0)))
      (entmake '((0 . "ENDBLK"))))
    (princ (strcat "\n23HG: block " "SOFA_3" " da co trong ban ve - giu dinh nghia cu")))
  (if (not (tblsearch "BLOCK" "BAN_TRA"))
    (progn
      (entmake '((0 . "BLOCK") (2 . "BAN_TRA") (70 . 0) (10 0.0 0.0 0.0)))
      (entmake '((0 . "LWPOLYLINE") (100 . "AcDbEntity") (8 . "0") (100 . "AcDbPolyline") (90 . 4) (70 . 1) (10 0.0 0.0) (10 1000.0 0.0) (10 1000.0 600.0) (10 0.0 600.0)))
      (entmake '((0 . "LWPOLYLINE") (100 . "AcDbEntity") (8 . "0") (100 . "AcDbPolyline") (90 . 4) (70 . 1) (10 60.0 60.0) (10 940.0 60.0) (10 940.0 540.0) (10 60.0 540.0)))
      (entmake '((0 . "ENDBLK"))))
    (princ (strcat "\n23HG: block " "BAN_TRA" " da co trong ban ve - giu dinh nghia cu")))
  (if (not (tblsearch "BLOCK" "BAN_AN_4"))
    (progn
      (entmake '((0 . "BLOCK") (2 . "BAN_AN_4") (70 . 0) (10 0.0 0.0 0.0)))
      (entmake '((0 . "LWPOLYLINE") (100 . "AcDbEntity") (8 . "0") (100 . "AcDbPolyline") (90 . 4) (70 . 1) (10 0.0 400.0) (10 1200.0 400.0) (10 1200.0 1200.0) (10 0.0 1200.0)))
      (entmake '((0 . "LWPOLYLINE") (100 . "AcDbEntity") (8 . "0") (100 . "AcDbPolyline") (90 . 8) (70 . 1) (10 145.0 0.0) (10 515.0 0.0) (10 555.0 40.0) (10 555.0 360.0) (10 515.0 400.0) (10 145.0 400.0) (10 105.0 360.0) (10 105.0 40.0)))
      (entmake '((0 . "LWPOLYLINE") (100 . "AcDbEntity") (8 . "0") (100 . "AcDbPolyline") (90 . 4) (70 . 1) (10 105.0 0.0) (10 555.0 0.0) (10 555.0 80.0) (10 105.0 80.0)))
      (entmake '((0 . "LWPOLYLINE") (100 . "AcDbEntity") (8 . "0") (100 . "AcDbPolyline") (90 . 8) (70 . 1) (10 145.0 1200.0) (10 515.0 1200.0) (10 555.0 1240.0) (10 555.0 1560.0) (10 515.0 1600.0) (10 145.0 1600.0) (10 105.0 1560.0) (10 105.0 1240.0)))
      (entmake '((0 . "LWPOLYLINE") (100 . "AcDbEntity") (8 . "0") (100 . "AcDbPolyline") (90 . 4) (70 . 1) (10 105.0 1520.0) (10 555.0 1520.0) (10 555.0 1600.0) (10 105.0 1600.0)))
      (entmake '((0 . "LWPOLYLINE") (100 . "AcDbEntity") (8 . "0") (100 . "AcDbPolyline") (90 . 8) (70 . 1) (10 685.0 0.0) (10 1055.0 0.0) (10 1095.0 40.0) (10 1095.0 360.0) (10 1055.0 400.0) (10 685.0 400.0) (10 645.0 360.0) (10 645.0 40.0)))
      (entmake '((0 . "LWPOLYLINE") (100 . "AcDbEntity") (8 . "0") (100 . "AcDbPolyline") (90 . 4) (70 . 1) (10 645.0 0.0) (10 1095.0 0.0) (10 1095.0 80.0) (10 645.0 80.0)))
      (entmake '((0 . "LWPOLYLINE") (100 . "AcDbEntity") (8 . "0") (100 . "AcDbPolyline") (90 . 8) (70 . 1) (10 685.0 1200.0) (10 1055.0 1200.0) (10 1095.0 1240.0) (10 1095.0 1560.0) (10 1055.0 1600.0) (10 685.0 1600.0) (10 645.0 1560.0) (10 645.0 1240.0)))
      (entmake '((0 . "LWPOLYLINE") (100 . "AcDbEntity") (8 . "0") (100 . "AcDbPolyline") (90 . 4) (70 . 1) (10 645.0 1520.0) (10 1095.0 1520.0) (10 1095.0 1600.0) (10 645.0 1600.0)))
      (entmake '((0 . "ENDBLK"))))
    (princ (strcat "\n23HG: block " "BAN_AN_4" " da co trong ban ve - giu dinh nghia cu")))
  (if (not (tblsearch "BLOCK" "TU_BEP"))
    (progn
      (entmake '((0 . "BLOCK") (2 . "TU_BEP") (70 . 0) (10 0.0 0.0 0.0)))
      (entmake '((0 . "LWPOLYLINE") (100 . "AcDbEntity") (8 . "0") (100 . "AcDbPolyline") (90 . 4) (70 . 1) (10 0.0 0.0) (10 2400.0 0.0) (10 2400.0 600.0) (10 0.0 600.0)))
      (entmake '((0 . "LINE") (8 . "0") (10 0.0 560.0 0.0) (11 2400.0 560.0 0.0)))
      (entmake '((0 . "LWPOLYLINE") (100 . "AcDbEntity") (8 . "0") (100 . "AcDbPolyline") (90 . 4) (70 . 1) (10 350.0 80.0) (10 1150.0 80.0) (10 1150.0 500.0) (10 350.0 500.0)))
      (entmake '((0 . "LWPOLYLINE") (100 . "AcDbEntity") (8 . "0") (100 . "AcDbPolyline") (90 . 8) (70 . 1) (10 460.0 120.0) (10 1040.0 120.0) (10 1100.0 180.0) (10 1100.0 400.0) (10 1040.0 460.0) (10 460.0 460.0) (10 400.0 400.0) (10 400.0 180.0)))
      (entmake '((0 . "CIRCLE") (8 . "0") (10 750.0 290.0 0.0) (40 . 25.0)))
      (entmake '((0 . "CIRCLE") (8 . "0") (10 750.0 45.0 0.0) (40 . 20.0)))
      (entmake '((0 . "LWPOLYLINE") (100 . "AcDbEntity") (8 . "0") (100 . "AcDbPolyline") (90 . 4) (70 . 1) (10 1500.0 80.0) (10 2200.0 80.0) (10 2200.0 500.0) (10 1500.0 500.0)))
      (entmake '((0 . "CIRCLE") (8 . "0") (10 1675.0 290.0 0.0) (40 . 120.0)))
      (entmake '((0 . "CIRCLE") (8 . "0") (10 1675.0 290.0 0.0) (40 . 60.0)))
      (entmake '((0 . "CIRCLE") (8 . "0") (10 2025.0 290.0 0.0) (40 . 120.0)))
      (entmake '((0 . "CIRCLE") (8 . "0") (10 2025.0 290.0 0.0) (40 . 60.0)))
      (entmake '((0 . "ENDBLK"))))
    (princ (strcat "\n23HG: block " "TU_BEP" " da co trong ban ve - giu dinh nghia cu")))
  (if (not (tblsearch "BLOCK" "BON_CAU"))
    (progn
      (entmake '((0 . "BLOCK") (2 . "BON_CAU") (70 . 0) (10 0.0 0.0 0.0)))
      (entmake '((0 . "LWPOLYLINE") (100 . "AcDbEntity") (8 . "0") (100 . "AcDbPolyline") (90 . 8) (70 . 1) (10 50.0 0.0) (10 350.0 0.0) (10 380.0 30.0) (10 380.0 150.0) (10 350.0 180.0) (10 50.0 180.0) (10 20.0 150.0) (10 20.0 30.0)))
      (entmake '((0 . "CIRCLE") (8 . "0") (10 200.0 90.0 0.0) (40 . 25.0)))
      (entmake '((0 . "LINE") (8 . "0") (10 70.0 180.0 0.0) (11 0.0 500.0 0.0)))
      (entmake '((0 . "LINE") (8 . "0") (10 330.0 180.0 0.0) (11 400.0 500.0 0.0)))
      (entmake '((0 . "ARC") (8 . "0") (10 200.0 500.0 0.0) (40 . 200.0) (50 . 0.0) (51 . 3.14159265359)))
      (entmake '((0 . "CIRCLE") (8 . "0") (10 200.0 480.0 0.0) (40 . 120.0)))
      (entmake '((0 . "ENDBLK"))))
    (princ (strcat "\n23HG: block " "BON_CAU" " da co trong ban ve - giu dinh nghia cu")))
  (if (not (tblsearch "BLOCK" "LAVABO"))
    (progn
      (entmake '((0 . "BLOCK") (2 . "LAVABO") (70 . 0) (10 0.0 0.0 0.0)))
      (entmake '((0 . "LWPOLYLINE") (100 . "AcDbEntity") (8 . "0") (100 . "AcDbPolyline") (90 . 6) (70 . 1) (10 0.0 0.0) (10 500.0 0.0) (10 500.0 320.0) (10 420.0 400.0) (10 80.0 400.0) (10 0.0 320.0)))
      (entmake '((0 . "CIRCLE") (8 . "0") (10 250.0 220.0 0.0) (40 . 150.0)))
      (entmake '((0 . "CIRCLE") (8 . "0") (10 250.0 220.0 0.0) (40 . 20.0)))
      (entmake '((0 . "CIRCLE") (8 . "0") (10 250.0 40.0 0.0) (40 . 20.0)))
      (entmake '((0 . "ENDBLK"))))
    (princ (strcat "\n23HG: block " "LAVABO" " da co trong ban ve - giu dinh nghia cu")))
  (princ))

(defun hg23:ve-1 ()
  (hg23:em "01/truc/V/1/line" '((0 . "LINE") (8 . "KT-TRUC") (10 0.0 -3400.0 0.0) (11 0.0 11800.0 0.0) (-3 ("23HG_CAD" (1000 . "01/truc/V/1/line") (1000 . "01")))))
  (hg23:em "01/truc/V/1/bubble/0" '((0 . "CIRCLE") (8 . "KT-TRUC-KH") (10 0.0 -3800.0 0.0) (40 . 400.0) (-3 ("23HG_CAD" (1000 . "01/truc/V/1/bubble/0") (1000 . "01")))))
  (hg23:em "01/truc/V/1/name/0" '((0 . "TEXT") (8 . "KT-TRUC-KH") (7 . "VN_ARIAL") (10 0.0 -3800.0 0.0) (11 0.0 -3800.0 0.0) (40 . 350.0) (1 . "1") (50 . 0.0) (72 . 1) (73 . 2) (-3 ("23HG_CAD" (1000 . "01/truc/V/1/name/0") (1000 . "01")))))
  (hg23:em "01/truc/V/1/bubble/1" '((0 . "CIRCLE") (8 . "KT-TRUC-KH") (10 0.0 12200.0 0.0) (40 . 400.0) (-3 ("23HG_CAD" (1000 . "01/truc/V/1/bubble/1") (1000 . "01")))))
  (hg23:em "01/truc/V/1/name/1" '((0 . "TEXT") (8 . "KT-TRUC-KH") (7 . "VN_ARIAL") (10 0.0 12200.0 0.0) (11 0.0 12200.0 0.0) (40 . 350.0) (1 . "1") (50 . 0.0) (72 . 1) (73 . 2) (-3 ("23HG_CAD" (1000 . "01/truc/V/1/name/1") (1000 . "01")))))
  (hg23:em "01/truc/V/2/line" '((0 . "LINE") (8 . "KT-TRUC") (10 3600.0 -3400.0 0.0) (11 3600.0 11800.0 0.0) (-3 ("23HG_CAD" (1000 . "01/truc/V/2/line") (1000 . "01")))))
  (hg23:em "01/truc/V/2/bubble/0" '((0 . "CIRCLE") (8 . "KT-TRUC-KH") (10 3600.0 -3800.0 0.0) (40 . 400.0) (-3 ("23HG_CAD" (1000 . "01/truc/V/2/bubble/0") (1000 . "01")))))
  (hg23:em "01/truc/V/2/name/0" '((0 . "TEXT") (8 . "KT-TRUC-KH") (7 . "VN_ARIAL") (10 3600.0 -3800.0 0.0) (11 3600.0 -3800.0 0.0) (40 . 350.0) (1 . "2") (50 . 0.0) (72 . 1) (73 . 2) (-3 ("23HG_CAD" (1000 . "01/truc/V/2/name/0") (1000 . "01")))))
  (hg23:em "01/truc/V/2/bubble/1" '((0 . "CIRCLE") (8 . "KT-TRUC-KH") (10 3600.0 12200.0 0.0) (40 . 400.0) (-3 ("23HG_CAD" (1000 . "01/truc/V/2/bubble/1") (1000 . "01")))))
  (hg23:em "01/truc/V/2/name/1" '((0 . "TEXT") (8 . "KT-TRUC-KH") (7 . "VN_ARIAL") (10 3600.0 12200.0 0.0) (11 3600.0 12200.0 0.0) (40 . 350.0) (1 . "2") (50 . 0.0) (72 . 1) (73 . 2) (-3 ("23HG_CAD" (1000 . "01/truc/V/2/name/1") (1000 . "01")))))
  (hg23:em "01/truc/V/3/line" '((0 . "LINE") (8 . "KT-TRUC") (10 7200.0 -3400.0 0.0) (11 7200.0 11800.0 0.0) (-3 ("23HG_CAD" (1000 . "01/truc/V/3/line") (1000 . "01")))))
  (hg23:em "01/truc/V/3/bubble/0" '((0 . "CIRCLE") (8 . "KT-TRUC-KH") (10 7200.0 -3800.0 0.0) (40 . 400.0) (-3 ("23HG_CAD" (1000 . "01/truc/V/3/bubble/0") (1000 . "01")))))
  (hg23:em "01/truc/V/3/name/0" '((0 . "TEXT") (8 . "KT-TRUC-KH") (7 . "VN_ARIAL") (10 7200.0 -3800.0 0.0) (11 7200.0 -3800.0 0.0) (40 . 350.0) (1 . "3") (50 . 0.0) (72 . 1) (73 . 2) (-3 ("23HG_CAD" (1000 . "01/truc/V/3/name/0") (1000 . "01")))))
  (hg23:em "01/truc/V/3/bubble/1" '((0 . "CIRCLE") (8 . "KT-TRUC-KH") (10 7200.0 12200.0 0.0) (40 . 400.0) (-3 ("23HG_CAD" (1000 . "01/truc/V/3/bubble/1") (1000 . "01")))))
  (hg23:em "01/truc/V/3/name/1" '((0 . "TEXT") (8 . "KT-TRUC-KH") (7 . "VN_ARIAL") (10 7200.0 12200.0 0.0) (11 7200.0 12200.0 0.0) (40 . 350.0) (1 . "3") (50 . 0.0) (72 . 1) (73 . 2) (-3 ("23HG_CAD" (1000 . "01/truc/V/3/name/1") (1000 . "01")))))
  (hg23:em "01/truc/V/4/line" '((0 . "LINE") (8 . "KT-TRUC") (10 10800.0 -3400.0 0.0) (11 10800.0 11800.0 0.0) (-3 ("23HG_CAD" (1000 . "01/truc/V/4/line") (1000 . "01")))))
  (hg23:em "01/truc/V/4/bubble/0" '((0 . "CIRCLE") (8 . "KT-TRUC-KH") (10 10800.0 -3800.0 0.0) (40 . 400.0) (-3 ("23HG_CAD" (1000 . "01/truc/V/4/bubble/0") (1000 . "01")))))
  (hg23:em "01/truc/V/4/name/0" '((0 . "TEXT") (8 . "KT-TRUC-KH") (7 . "VN_ARIAL") (10 10800.0 -3800.0 0.0) (11 10800.0 -3800.0 0.0) (40 . 350.0) (1 . "4") (50 . 0.0) (72 . 1) (73 . 2) (-3 ("23HG_CAD" (1000 . "01/truc/V/4/name/0") (1000 . "01")))))
  (hg23:em "01/truc/V/4/bubble/1" '((0 . "CIRCLE") (8 . "KT-TRUC-KH") (10 10800.0 12200.0 0.0) (40 . 400.0) (-3 ("23HG_CAD" (1000 . "01/truc/V/4/bubble/1") (1000 . "01")))))
  (hg23:em "01/truc/V/4/name/1" '((0 . "TEXT") (8 . "KT-TRUC-KH") (7 . "VN_ARIAL") (10 10800.0 12200.0 0.0) (11 10800.0 12200.0 0.0) (40 . 350.0) (1 . "4") (50 . 0.0) (72 . 1) (73 . 2) (-3 ("23HG_CAD" (1000 . "01/truc/V/4/name/1") (1000 . "01")))))
  (hg23:em "01/truc/H/A/line" '((0 . "LINE") (8 . "KT-TRUC") (10 -3400.0 0.0 0.0) (11 14200.0 0.0 0.0) (-3 ("23HG_CAD" (1000 . "01/truc/H/A/line") (1000 . "01")))))
  (hg23:em "01/truc/H/A/bubble/0" '((0 . "CIRCLE") (8 . "KT-TRUC-KH") (10 -3800.0 0.0 0.0) (40 . 400.0) (-3 ("23HG_CAD" (1000 . "01/truc/H/A/bubble/0") (1000 . "01")))))
  (hg23:em "01/truc/H/A/name/0" '((0 . "TEXT") (8 . "KT-TRUC-KH") (7 . "VN_ARIAL") (10 -3800.0 0.0 0.0) (11 -3800.0 0.0 0.0) (40 . 350.0) (1 . "A") (50 . 0.0) (72 . 1) (73 . 2) (-3 ("23HG_CAD" (1000 . "01/truc/H/A/name/0") (1000 . "01")))))
  (hg23:em "01/truc/H/A/bubble/1" '((0 . "CIRCLE") (8 . "KT-TRUC-KH") (10 14600.0 0.0 0.0) (40 . 400.0) (-3 ("23HG_CAD" (1000 . "01/truc/H/A/bubble/1") (1000 . "01")))))
  (hg23:em "01/truc/H/A/name/1" '((0 . "TEXT") (8 . "KT-TRUC-KH") (7 . "VN_ARIAL") (10 14600.0 0.0 0.0) (11 14600.0 0.0 0.0) (40 . 350.0) (1 . "A") (50 . 0.0) (72 . 1) (73 . 2) (-3 ("23HG_CAD" (1000 . "01/truc/H/A/name/1") (1000 . "01")))))
  (hg23:em "01/truc/H/B/line" '((0 . "LINE") (8 . "KT-TRUC") (10 -3400.0 4200.0 0.0) (11 14200.0 4200.0 0.0) (-3 ("23HG_CAD" (1000 . "01/truc/H/B/line") (1000 . "01")))))
  (hg23:em "01/truc/H/B/bubble/0" '((0 . "CIRCLE") (8 . "KT-TRUC-KH") (10 -3800.0 4200.0 0.0) (40 . 400.0) (-3 ("23HG_CAD" (1000 . "01/truc/H/B/bubble/0") (1000 . "01")))))
  (hg23:em "01/truc/H/B/name/0" '((0 . "TEXT") (8 . "KT-TRUC-KH") (7 . "VN_ARIAL") (10 -3800.0 4200.0 0.0) (11 -3800.0 4200.0 0.0) (40 . 350.0) (1 . "B") (50 . 0.0) (72 . 1) (73 . 2) (-3 ("23HG_CAD" (1000 . "01/truc/H/B/name/0") (1000 . "01")))))
  (hg23:em "01/truc/H/B/bubble/1" '((0 . "CIRCLE") (8 . "KT-TRUC-KH") (10 14600.0 4200.0 0.0) (40 . 400.0) (-3 ("23HG_CAD" (1000 . "01/truc/H/B/bubble/1") (1000 . "01")))))
  (hg23:em "01/truc/H/B/name/1" '((0 . "TEXT") (8 . "KT-TRUC-KH") (7 . "VN_ARIAL") (10 14600.0 4200.0 0.0) (11 14600.0 4200.0 0.0) (40 . 350.0) (1 . "B") (50 . 0.0) (72 . 1) (73 . 2) (-3 ("23HG_CAD" (1000 . "01/truc/H/B/name/1") (1000 . "01")))))
  (hg23:em "01/truc/H/C/line" '((0 . "LINE") (8 . "KT-TRUC") (10 -3400.0 8400.0 0.0) (11 14200.0 8400.0 0.0) (-3 ("23HG_CAD" (1000 . "01/truc/H/C/line") (1000 . "01")))))
  (hg23:em "01/truc/H/C/bubble/0" '((0 . "CIRCLE") (8 . "KT-TRUC-KH") (10 -3800.0 8400.0 0.0) (40 . 400.0) (-3 ("23HG_CAD" (1000 . "01/truc/H/C/bubble/0") (1000 . "01")))))
  (hg23:em "01/truc/H/C/name/0" '((0 . "TEXT") (8 . "KT-TRUC-KH") (7 . "VN_ARIAL") (10 -3800.0 8400.0 0.0) (11 -3800.0 8400.0 0.0) (40 . 350.0) (1 . "C") (50 . 0.0) (72 . 1) (73 . 2) (-3 ("23HG_CAD" (1000 . "01/truc/H/C/name/0") (1000 . "01")))))
  (hg23:em "01/truc/H/C/bubble/1" '((0 . "CIRCLE") (8 . "KT-TRUC-KH") (10 14600.0 8400.0 0.0) (40 . 400.0) (-3 ("23HG_CAD" (1000 . "01/truc/H/C/bubble/1") (1000 . "01")))))
  (hg23:em "01/truc/H/C/name/1" '((0 . "TEXT") (8 . "KT-TRUC-KH") (7 . "VN_ARIAL") (10 14600.0 8400.0 0.0) (11 14600.0 8400.0 0.0) (40 . 350.0) (1 . "C") (50 . 0.0) (72 . 1) (73 . 2) (-3 ("23HG_CAD" (1000 . "01/truc/H/C/name/1") (1000 . "01")))))
  (hg23:em "02/cot/C-1A" '((0 . "LWPOLYLINE") (100 . "AcDbEntity") (8 . "KC-COT") (100 . "AcDbPolyline") (90 . 4) (70 . 1) (10 -110.0 -110.0) (10 110.0 -110.0) (10 110.0 110.0) (10 -110.0 110.0) (-3 ("23HG_CAD" (1000 . "02/cot/C-1A") (1000 . "02")))))
  (hg23:em "02/cot/C-2A" '((0 . "LWPOLYLINE") (100 . "AcDbEntity") (8 . "KC-COT") (100 . "AcDbPolyline") (90 . 4) (70 . 1) (10 3490.0 -110.0) (10 3710.0 -110.0) (10 3710.0 110.0) (10 3490.0 110.0) (-3 ("23HG_CAD" (1000 . "02/cot/C-2A") (1000 . "02")))))
  (hg23:em "02/cot/C-3A" '((0 . "LWPOLYLINE") (100 . "AcDbEntity") (8 . "KC-COT") (100 . "AcDbPolyline") (90 . 4) (70 . 1) (10 7090.0 -110.0) (10 7310.0 -110.0) (10 7310.0 110.0) (10 7090.0 110.0) (-3 ("23HG_CAD" (1000 . "02/cot/C-3A") (1000 . "02")))))
  (hg23:em "02/cot/C-4A" '((0 . "LWPOLYLINE") (100 . "AcDbEntity") (8 . "KC-COT") (100 . "AcDbPolyline") (90 . 4) (70 . 1) (10 10690.0 -110.0) (10 10910.0 -110.0) (10 10910.0 110.0) (10 10690.0 110.0) (-3 ("23HG_CAD" (1000 . "02/cot/C-4A") (1000 . "02")))))
  (hg23:em "02/cot/C-1B" '((0 . "LWPOLYLINE") (100 . "AcDbEntity") (8 . "KC-COT") (100 . "AcDbPolyline") (90 . 4) (70 . 1) (10 -110.0 4090.0) (10 110.0 4090.0) (10 110.0 4310.0) (10 -110.0 4310.0) (-3 ("23HG_CAD" (1000 . "02/cot/C-1B") (1000 . "02")))))
  (hg23:em "02/cot/C-2B" '((0 . "LWPOLYLINE") (100 . "AcDbEntity") (8 . "KC-COT") (100 . "AcDbPolyline") (90 . 4) (70 . 1) (10 3490.0 4090.0) (10 3710.0 4090.0) (10 3710.0 4310.0) (10 3490.0 4310.0) (-3 ("23HG_CAD" (1000 . "02/cot/C-2B") (1000 . "02")))))
  (hg23:em "02/cot/C-3B" '((0 . "LWPOLYLINE") (100 . "AcDbEntity") (8 . "KC-COT") (100 . "AcDbPolyline") (90 . 4) (70 . 1) (10 7090.0 4090.0) (10 7310.0 4090.0) (10 7310.0 4310.0) (10 7090.0 4310.0) (-3 ("23HG_CAD" (1000 . "02/cot/C-3B") (1000 . "02")))))
  (hg23:em "02/cot/C-4B" '((0 . "LWPOLYLINE") (100 . "AcDbEntity") (8 . "KC-COT") (100 . "AcDbPolyline") (90 . 4) (70 . 1) (10 10690.0 4090.0) (10 10910.0 4090.0) (10 10910.0 4310.0) (10 10690.0 4310.0) (-3 ("23HG_CAD" (1000 . "02/cot/C-4B") (1000 . "02")))))
  (hg23:em "02/cot/C-1C" '((0 . "LWPOLYLINE") (100 . "AcDbEntity") (8 . "KC-COT") (100 . "AcDbPolyline") (90 . 4) (70 . 1) (10 -110.0 8290.0) (10 110.0 8290.0) (10 110.0 8510.0) (10 -110.0 8510.0) (-3 ("23HG_CAD" (1000 . "02/cot/C-1C") (1000 . "02")))))
  (hg23:em "02/cot/C-2C" '((0 . "LWPOLYLINE") (100 . "AcDbEntity") (8 . "KC-COT") (100 . "AcDbPolyline") (90 . 4) (70 . 1) (10 3490.0 8290.0) (10 3710.0 8290.0) (10 3710.0 8510.0) (10 3490.0 8510.0) (-3 ("23HG_CAD" (1000 . "02/cot/C-2C") (1000 . "02")))))
  (hg23:em "02/cot/C-3C" '((0 . "LWPOLYLINE") (100 . "AcDbEntity") (8 . "KC-COT") (100 . "AcDbPolyline") (90 . 4) (70 . 1) (10 7090.0 8290.0) (10 7310.0 8290.0) (10 7310.0 8510.0) (10 7090.0 8510.0) (-3 ("23HG_CAD" (1000 . "02/cot/C-3C") (1000 . "02")))))
  (hg23:em "02/cot/C-4C" '((0 . "LWPOLYLINE") (100 . "AcDbEntity") (8 . "KC-COT") (100 . "AcDbPolyline") (90 . 4) (70 . 1) (10 10690.0 8290.0) (10 10910.0 8290.0) (10 10910.0 8510.0) (10 10690.0 8510.0) (-3 ("23HG_CAD" (1000 . "02/cot/C-4C") (1000 . "02")))))
  (hg23:em "03/tuong/outline/0" '((0 . "LWPOLYLINE") (100 . "AcDbEntity") (8 . "KT-TUONG") (100 . "AcDbPolyline") (90 . 2) (70 . 0) (10 -110.0 110.0) (10 -110.0 4090.0) (-3 ("23HG_CAD" (1000 . "03/tuong/outline/0") (1000 . "03")))))
  (hg23:em "03/tuong/outline/1" '((0 . "LWPOLYLINE") (100 . "AcDbEntity") (8 . "KT-TUONG") (100 . "AcDbPolyline") (90 . 4) (70 . 0) (10 -110.0 4310.0) (10 -110.0 5700.0) (10 110.0 5700.0) (10 110.0 4310.0) (-3 ("23HG_CAD" (1000 . "03/tuong/outline/1") (1000 . "03")))))
  (hg23:em "03/tuong/outline/2" '((0 . "LWPOLYLINE") (100 . "AcDbEntity") (8 . "KT-TUONG") (100 . "AcDbPolyline") (90 . 5) (70 . 0) (10 3490.0 8290.0) (10 110.0 8290.0) (10 110.0 6900.0) (10 -110.0 6900.0) (10 -110.0 8290.0) (-3 ("23HG_CAD" (1000 . "03/tuong/outline/2") (1000 . "03")))))
  (hg23:em "03/tuong/outline/3" '((0 . "LWPOLYLINE") (100 . "AcDbEntity") (8 . "KT-TUONG") (100 . "AcDbPolyline") (90 . 5) (70 . 0) (10 110.0 4090.0) (10 110.0 110.0) (10 1000.0 110.0) (10 1000.0 -110.0) (10 110.0 -110.0) (-3 ("23HG_CAD" (1000 . "03/tuong/outline/3") (1000 . "03")))))
  (hg23:em "03/tuong/outline/4" '((0 . "LWPOLYLINE") (100 . "AcDbEntity") (8 . "KT-TUONG") (100 . "AcDbPolyline") (90 . 4) (70 . 0) (10 110.0 4255.0) (10 2400.0 4255.0) (10 2400.0 4145.0) (10 110.0 4145.0) (-3 ("23HG_CAD" (1000 . "03/tuong/outline/4") (1000 . "03")))))
  (hg23:em "03/tuong/outline/5" '((0 . "LWPOLYLINE") (100 . "AcDbEntity") (8 . "KT-TUONG") (100 . "AcDbPolyline") (90 . 2) (70 . 0) (10 110.0 8510.0) (10 3490.0 8510.0) (-3 ("23HG_CAD" (1000 . "03/tuong/outline/5") (1000 . "03")))))
  (hg23:em "03/tuong/outline/6" '((0 . "LWPOLYLINE") (100 . "AcDbEntity") (8 . "KT-TUONG") (100 . "AcDbPolyline") (90 . 4) (70 . 0) (10 3490.0 -110.0) (10 2600.0 -110.0) (10 2600.0 110.0) (10 3490.0 110.0) (-3 ("23HG_CAD" (1000 . "03/tuong/outline/6") (1000 . "03")))))
  (hg23:em "03/tuong/outline/7" '((0 . "LWPOLYLINE") (100 . "AcDbEntity") (8 . "KT-TUONG") (100 . "AcDbPolyline") (90 . 4) (70 . 0) (10 3490.0 4145.0) (10 3300.0 4145.0) (10 3300.0 4255.0) (10 3490.0 4255.0) (-3 ("23HG_CAD" (1000 . "03/tuong/outline/7") (1000 . "03")))))
  (hg23:em "03/tuong/outline/8" '((0 . "LWPOLYLINE") (100 . "AcDbEntity") (8 . "KT-TUONG") (100 . "AcDbPolyline") (90 . 2) (70 . 0) (10 3545.0 4310.0) (10 3545.0 8290.0) (-3 ("23HG_CAD" (1000 . "03/tuong/outline/8") (1000 . "03")))))
  (hg23:em "03/tuong/outline/9" '((0 . "LWPOLYLINE") (100 . "AcDbEntity") (8 . "KT-TUONG") (100 . "AcDbPolyline") (90 . 2) (70 . 0) (10 3655.0 8290.0) (10 3655.0 4310.0) (-3 ("23HG_CAD" (1000 . "03/tuong/outline/9") (1000 . "03")))))
  (hg23:em "03/tuong/outline/10" '((0 . "LWPOLYLINE") (100 . "AcDbEntity") (8 . "KT-TUONG") (100 . "AcDbPolyline") (90 . 4) (70 . 0) (10 3710.0 110.0) (10 4600.0 110.0) (10 4600.0 -110.0) (10 3710.0 -110.0) (-3 ("23HG_CAD" (1000 . "03/tuong/outline/10") (1000 . "03")))))
  (hg23:em "03/tuong/outline/11" '((0 . "LWPOLYLINE") (100 . "AcDbEntity") (8 . "KT-TUONG") (100 . "AcDbPolyline") (90 . 4) (70 . 0) (10 3710.0 8510.0) (10 4800.0 8510.0) (10 4800.0 8290.0) (10 3710.0 8290.0) (-3 ("23HG_CAD" (1000 . "03/tuong/outline/11") (1000 . "03")))))
  (hg23:em "03/tuong/outline/12" '((0 . "LWPOLYLINE") (100 . "AcDbEntity") (8 . "KT-TUONG") (100 . "AcDbPolyline") (90 . 4) (70 . 0) (10 7090.0 8290.0) (10 6000.0 8290.0) (10 6000.0 8510.0) (10 7090.0 8510.0) (-3 ("23HG_CAD" (1000 . "03/tuong/outline/12") (1000 . "03")))))
  (hg23:em "03/tuong/outline/13" '((0 . "LWPOLYLINE") (100 . "AcDbEntity") (8 . "KT-TUONG") (100 . "AcDbPolyline") (90 . 4) (70 . 0) (10 7090.0 -110.0) (10 6400.0 -110.0) (10 6400.0 110.0) (10 7090.0 110.0) (-3 ("23HG_CAD" (1000 . "03/tuong/outline/13") (1000 . "03")))))
  (hg23:em "03/tuong/outline/14" '((0 . "LWPOLYLINE") (100 . "AcDbEntity") (8 . "KT-TUONG") (100 . "AcDbPolyline") (90 . 4) (70 . 0) (10 7145.0 4310.0) (10 7145.0 4800.0) (10 7255.0 4800.0) (10 7255.0 4310.0) (-3 ("23HG_CAD" (1000 . "03/tuong/outline/14") (1000 . "03")))))
  (hg23:em "03/tuong/outline/15" '((0 . "LWPOLYLINE") (100 . "AcDbEntity") (8 . "KT-TUONG") (100 . "AcDbPolyline") (90 . 13) (70 . 0) (10 10690.0 4310.0) (10 10690.0 6145.0) (10 7255.0 6145.0) (10 7255.0 5500.0) (10 7145.0 5500.0) (10 7145.0 6145.0) (10 7145.0 6255.0) (10 7145.0 6800.0) (10 7255.0 6800.0) (10 7255.0 6255.0) (10 10690.0 6255.0) (10 10690.0 8290.0) (10 7310.0 8290.0) (-3 ("23HG_CAD" (1000 . "03/tuong/outline/15") (1000 . "03")))))
  (hg23:em "03/tuong/outline/16" '((0 . "LWPOLYLINE") (100 . "AcDbEntity") (8 . "KT-TUONG") (100 . "AcDbPolyline") (90 . 4) (70 . 0) (10 7255.0 8290.0) (10 7255.0 7700.0) (10 7145.0 7700.0) (10 7145.0 8290.0) (-3 ("23HG_CAD" (1000 . "03/tuong/outline/16") (1000 . "03")))))
  (hg23:em "03/tuong/outline/17" '((0 . "LWPOLYLINE") (100 . "AcDbEntity") (8 . "KT-TUONG") (100 . "AcDbPolyline") (90 . 4) (70 . 0) (10 7310.0 110.0) (10 8100.0 110.0) (10 8100.0 -110.0) (10 7310.0 -110.0) (-3 ("23HG_CAD" (1000 . "03/tuong/outline/17") (1000 . "03")))))
  (hg23:em "03/tuong/outline/18" '((0 . "LWPOLYLINE") (100 . "AcDbEntity") (8 . "KT-TUONG") (100 . "AcDbPolyline") (90 . 2) (70 . 0) (10 10690.0 4145.0) (10 7310.0 4145.0) (-3 ("23HG_CAD" (1000 . "03/tuong/outline/18") (1000 . "03")))))
  (hg23:em "03/tuong/outline/19" '((0 . "LWPOLYLINE") (100 . "AcDbEntity") (8 . "KT-TUONG") (100 . "AcDbPolyline") (90 . 2) (70 . 0) (10 7310.0 4255.0) (10 10690.0 4255.0) (-3 ("23HG_CAD" (1000 . "03/tuong/outline/19") (1000 . "03")))))
  (hg23:em "03/tuong/outline/20" '((0 . "LWPOLYLINE") (100 . "AcDbEntity") (8 . "KT-TUONG") (100 . "AcDbPolyline") (90 . 2) (70 . 0) (10 7310.0 8510.0) (10 10690.0 8510.0) (-3 ("23HG_CAD" (1000 . "03/tuong/outline/20") (1000 . "03")))))
  (hg23:em "03/tuong/outline/21" '((0 . "LWPOLYLINE") (100 . "AcDbEntity") (8 . "KT-TUONG") (100 . "AcDbPolyline") (90 . 5) (70 . 0) (10 10690.0 -110.0) (10 9600.0 -110.0) (10 9600.0 110.0) (10 10690.0 110.0) (10 10690.0 4090.0) (-3 ("23HG_CAD" (1000 . "03/tuong/outline/21") (1000 . "03")))))
  (hg23:em "03/tuong/outline/22" '((0 . "LWPOLYLINE") (100 . "AcDbEntity") (8 . "KT-TUONG") (100 . "AcDbPolyline") (90 . 2) (70 . 0) (10 10910.0 4090.0) (10 10910.0 110.0) (-3 ("23HG_CAD" (1000 . "03/tuong/outline/22") (1000 . "03")))))
  (hg23:em "03/tuong/outline/23" '((0 . "LWPOLYLINE") (100 . "AcDbEntity") (8 . "KT-TUONG") (100 . "AcDbPolyline") (90 . 4) (70 . 0) (10 10910.0 8290.0) (10 10910.0 6255.0) (10 10910.0 6145.0) (10 10910.0 4310.0) (-3 ("23HG_CAD" (1000 . "03/tuong/outline/23") (1000 . "03")))))
  (hg23:em "04/cua/CD1/leaf/0" '((0 . "LINE") (8 . "KT-CUA") (10 1000.0 110.0 0.0) (11 1000.0 910.0 0.0) (-3 ("23HG_CAD" (1000 . "04/cua/CD1/leaf/0") (1000 . "04")))))
  (hg23:em "04/cua/CD1/arc/0" '((0 . "ARC") (8 . "KT-CUA") (10 1000.0 110.0 0.0) (40 . 800.0) (50 . 0.0) (51 . 1.570796326795) (-3 ("23HG_CAD" (1000 . "04/cua/CD1/arc/0") (1000 . "04")))))
  (hg23:em "04/cua/CD1/leaf/1" '((0 . "LINE") (8 . "KT-CUA") (10 2600.0 110.0 0.0) (11 2600.0 910.0 0.0) (-3 ("23HG_CAD" (1000 . "04/cua/CD1/leaf/1") (1000 . "04")))))
  (hg23:em "04/cua/CD1/arc/1" '((0 . "ARC") (8 . "KT-CUA") (10 2600.0 110.0 0.0) (40 . 800.0) (50 . 1.570796326795) (51 . 3.14159265359) (-3 ("23HG_CAD" (1000 . "04/cua/CD1/arc/1") (1000 . "04")))))
  (hg23:em "04/cua_kh/CD1" '((0 . "TEXT") (8 . "KT-CUA-KH") (7 . "VN_ARIAL") (10 1800.0 -360.0 0.0) (11 1800.0 -360.0 0.0) (40 . 200.0) (1 . "D1") (50 . 0.0) (72 . 1) (73 . 2) (-3 ("23HG_CAD" (1000 . "04/cua_kh/CD1") (1000 . "04")))))
  (hg23:em "04/cua/CD2/leaf/0" '((0 . "LINE") (8 . "KT-CUA") (10 3300.0 4255.0 0.0) (11 3300.0 5155.0 0.0) (-3 ("23HG_CAD" (1000 . "04/cua/CD2/leaf/0") (1000 . "04")))))
  (hg23:em "04/cua/CD2/arc/0" '((0 . "ARC") (8 . "KT-CUA") (10 3300.0 4255.0 0.0) (40 . 900.0) (50 . 1.570796326795) (51 . 3.14159265359) (-3 ("23HG_CAD" (1000 . "04/cua/CD2/arc/0") (1000 . "04")))))
  (hg23:em "04/cua_kh/CD2" '((0 . "TEXT") (8 . "KT-CUA-KH") (7 . "VN_ARIAL") (10 2850.0 3895.0 0.0) (11 2850.0 3895.0 0.0) (40 . 200.0) (1 . "D2") (50 . 0.0) (72 . 1) (73 . 2) (-3 ("23HG_CAD" (1000 . "04/cua_kh/CD2") (1000 . "04")))))
  (hg23:em "04/cua/CD3/leaf/0" '((0 . "LINE") (8 . "KT-CUA") (10 7255.0 4800.0 0.0) (11 7955.0 4800.0 0.0) (-3 ("23HG_CAD" (1000 . "04/cua/CD3/leaf/0") (1000 . "04")))))
  (hg23:em "04/cua/CD3/arc/0" '((0 . "ARC") (8 . "KT-CUA") (10 7255.0 4800.0 0.0) (40 . 700.0) (50 . 0.0) (51 . 1.570796326795) (-3 ("23HG_CAD" (1000 . "04/cua/CD3/arc/0") (1000 . "04")))))
  (hg23:em "04/cua_kh/CD3" '((0 . "TEXT") (8 . "KT-CUA-KH") (7 . "VN_ARIAL") (10 6895.0 5150.0 0.0) (11 6895.0 5150.0 0.0) (40 . 200.0) (1 . "D3") (50 . 1.570796326795) (72 . 1) (73 . 2) (-3 ("23HG_CAD" (1000 . "04/cua_kh/CD3") (1000 . "04")))))
  (hg23:em "04/cua/CD4/leaf/0" '((0 . "LINE") (8 . "KT-CUA") (10 7255.0 6800.0 0.0) (11 8155.0 6800.0 0.0) (-3 ("23HG_CAD" (1000 . "04/cua/CD4/leaf/0") (1000 . "04")))))
  (hg23:em "04/cua/CD4/arc/0" '((0 . "ARC") (8 . "KT-CUA") (10 7255.0 6800.0 0.0) (40 . 900.0) (50 . 0.0) (51 . 1.570796326795) (-3 ("23HG_CAD" (1000 . "04/cua/CD4/arc/0") (1000 . "04")))))
  (hg23:em "04/cua_kh/CD4" '((0 . "TEXT") (8 . "KT-CUA-KH") (7 . "VN_ARIAL") (10 6895.0 7250.0 0.0) (11 6895.0 7250.0 0.0) (40 . 200.0) (1 . "D2") (50 . 1.570796326795) (72 . 1) (73 . 2) (-3 ("23HG_CAD" (1000 . "04/cua_kh/CD4") (1000 . "04")))))
  (hg23:em "04/cua/CS1/line/0" '((0 . "LINE") (8 . "KT-CUA") (10 8100.0 -110.0 0.0) (11 9600.0 -110.0 0.0) (-3 ("23HG_CAD" (1000 . "04/cua/CS1/line/0") (1000 . "04")))))
  (hg23:em "04/cua/CS1/line/1" '((0 . "LINE") (8 . "KT-CUA") (10 8100.0 -25.0 0.0) (11 9600.0 -25.0 0.0) (-3 ("23HG_CAD" (1000 . "04/cua/CS1/line/1") (1000 . "04")))))
  (hg23:em "04/cua/CS1/line/2" '((0 . "LINE") (8 . "KT-CUA") (10 8100.0 25.0 0.0) (11 9600.0 25.0 0.0) (-3 ("23HG_CAD" (1000 . "04/cua/CS1/line/2") (1000 . "04")))))
  (hg23:em "04/cua/CS1/line/3" '((0 . "LINE") (8 . "KT-CUA") (10 8100.0 110.0 0.0) (11 9600.0 110.0 0.0) (-3 ("23HG_CAD" (1000 . "04/cua/CS1/line/3") (1000 . "04")))))
  (hg23:em "04/cua/CS1/line/4" '((0 . "LINE") (8 . "KT-CUA") (10 8100.0 -110.0 0.0) (11 8100.0 110.0 0.0) (-3 ("23HG_CAD" (1000 . "04/cua/CS1/line/4") (1000 . "04")))))
  (hg23:em "04/cua/CS1/line/5" '((0 . "LINE") (8 . "KT-CUA") (10 9600.0 -110.0 0.0) (11 9600.0 110.0 0.0) (-3 ("23HG_CAD" (1000 . "04/cua/CS1/line/5") (1000 . "04")))))
  (hg23:em "04/cua_kh/CS1" '((0 . "TEXT") (8 . "KT-CUA-KH") (7 . "VN_ARIAL") (10 8850.0 -360.0 0.0) (11 8850.0 -360.0 0.0) (40 . 200.0) (1 . "S1") (50 . 0.0) (72 . 1) (73 . 2) (-3 ("23HG_CAD" (1000 . "04/cua_kh/CS1") (1000 . "04")))))
  (hg23:em "04/cua/CS2/line/0" '((0 . "LINE") (8 . "KT-CUA") (10 4600.0 -110.0 0.0) (11 6400.0 -110.0 0.0) (-3 ("23HG_CAD" (1000 . "04/cua/CS2/line/0") (1000 . "04")))))
  (hg23:em "04/cua/CS2/line/1" '((0 . "LINE") (8 . "KT-CUA") (10 4600.0 -25.0 0.0) (11 6400.0 -25.0 0.0) (-3 ("23HG_CAD" (1000 . "04/cua/CS2/line/1") (1000 . "04")))))
  (hg23:em "04/cua/CS2/line/2" '((0 . "LINE") (8 . "KT-CUA") (10 4600.0 25.0 0.0) (11 6400.0 25.0 0.0) (-3 ("23HG_CAD" (1000 . "04/cua/CS2/line/2") (1000 . "04")))))
  (hg23:em "04/cua/CS2/line/3" '((0 . "LINE") (8 . "KT-CUA") (10 4600.0 110.0 0.0) (11 6400.0 110.0 0.0) (-3 ("23HG_CAD" (1000 . "04/cua/CS2/line/3") (1000 . "04")))))
  (hg23:em "04/cua/CS2/line/4" '((0 . "LINE") (8 . "KT-CUA") (10 4600.0 -110.0 0.0) (11 4600.0 110.0 0.0) (-3 ("23HG_CAD" (1000 . "04/cua/CS2/line/4") (1000 . "04")))))
  (hg23:em "04/cua/CS2/line/5" '((0 . "LINE") (8 . "KT-CUA") (10 6400.0 -110.0 0.0) (11 6400.0 110.0 0.0) (-3 ("23HG_CAD" (1000 . "04/cua/CS2/line/5") (1000 . "04")))))
  (hg23:em "04/cua_kh/CS2" '((0 . "TEXT") (8 . "KT-CUA-KH") (7 . "VN_ARIAL") (10 5500.0 -360.0 0.0) (11 5500.0 -360.0 0.0) (40 . 200.0) (1 . "S2") (50 . 0.0) (72 . 1) (73 . 2) (-3 ("23HG_CAD" (1000 . "04/cua_kh/CS2") (1000 . "04")))))
  (hg23:em "04/cua/CS3/line/0" '((0 . "LINE") (8 . "KT-CUA") (10 -110.0 6900.0 0.0) (11 -110.0 5700.0 0.0) (-3 ("23HG_CAD" (1000 . "04/cua/CS3/line/0") (1000 . "04")))))
  (hg23:em "04/cua/CS3/line/1" '((0 . "LINE") (8 . "KT-CUA") (10 -25.0 6900.0 0.0) (11 -25.0 5700.0 0.0) (-3 ("23HG_CAD" (1000 . "04/cua/CS3/line/1") (1000 . "04")))))
  (hg23:em "04/cua/CS3/line/2" '((0 . "LINE") (8 . "KT-CUA") (10 25.0 6900.0 0.0) (11 25.0 5700.0 0.0) (-3 ("23HG_CAD" (1000 . "04/cua/CS3/line/2") (1000 . "04")))))
  (hg23:em "04/cua/CS3/line/3" '((0 . "LINE") (8 . "KT-CUA") (10 110.0 6900.0 0.0) (11 110.0 5700.0 0.0) (-3 ("23HG_CAD" (1000 . "04/cua/CS3/line/3") (1000 . "04")))))
  (hg23:em "04/cua/CS3/line/4" '((0 . "LINE") (8 . "KT-CUA") (10 -110.0 6900.0 0.0) (11 110.0 6900.0 0.0) (-3 ("23HG_CAD" (1000 . "04/cua/CS3/line/4") (1000 . "04")))))
  (hg23:em "04/cua/CS3/line/5" '((0 . "LINE") (8 . "KT-CUA") (10 -110.0 5700.0 0.0) (11 110.0 5700.0 0.0) (-3 ("23HG_CAD" (1000 . "04/cua/CS3/line/5") (1000 . "04")))))
  (hg23:em "04/cua_kh/CS3" '((0 . "TEXT") (8 . "KT-CUA-KH") (7 . "VN_ARIAL") (10 -360.0 6300.0 0.0) (11 -360.0 6300.0 0.0) (40 . 200.0) (1 . "S3") (50 . 1.570796326795) (72 . 1) (73 . 2) (-3 ("23HG_CAD" (1000 . "04/cua_kh/CS3") (1000 . "04")))))
  (hg23:em "04/cua/CS4/line/0" '((0 . "LINE") (8 . "KT-CUA") (10 6000.0 8510.0 0.0) (11 4800.0 8510.0 0.0) (-3 ("23HG_CAD" (1000 . "04/cua/CS4/line/0") (1000 . "04")))))
  (hg23:em "04/cua/CS4/line/1" '((0 . "LINE") (8 . "KT-CUA") (10 6000.0 8425.0 0.0) (11 4800.0 8425.0 0.0) (-3 ("23HG_CAD" (1000 . "04/cua/CS4/line/1") (1000 . "04")))))
  (hg23:em "04/cua/CS4/line/2" '((0 . "LINE") (8 . "KT-CUA") (10 6000.0 8375.0 0.0) (11 4800.0 8375.0 0.0) (-3 ("23HG_CAD" (1000 . "04/cua/CS4/line/2") (1000 . "04")))))
  (hg23:em "04/cua/CS4/line/3" '((0 . "LINE") (8 . "KT-CUA") (10 6000.0 8290.0 0.0) (11 4800.0 8290.0 0.0) (-3 ("23HG_CAD" (1000 . "04/cua/CS4/line/3") (1000 . "04")))))
  (hg23:em "04/cua/CS4/line/4" '((0 . "LINE") (8 . "KT-CUA") (10 6000.0 8510.0 0.0) (11 6000.0 8290.0 0.0) (-3 ("23HG_CAD" (1000 . "04/cua/CS4/line/4") (1000 . "04")))))
  (hg23:em "04/cua/CS4/line/5" '((0 . "LINE") (8 . "KT-CUA") (10 4800.0 8510.0 0.0) (11 4800.0 8290.0 0.0) (-3 ("23HG_CAD" (1000 . "04/cua/CS4/line/5") (1000 . "04")))))
  (hg23:em "04/cua_kh/CS4" '((0 . "TEXT") (8 . "KT-CUA-KH") (7 . "VN_ARIAL") (10 5400.0 8760.0 0.0) (11 5400.0 8760.0 0.0) (40 . 200.0) (1 . "S3") (50 . 0.0) (72 . 1) (73 . 2) (-3 ("23HG_CAD" (1000 . "04/cua_kh/CS4") (1000 . "04")))))
  (hg23:em "05/thang/ST1/0/bao" '((0 . "LWPOLYLINE") (100 . "AcDbEntity") (8 . "KT-THANG") (100 . "AcDbPolyline") (90 . 4) (70 . 1) (10 3900.0 4900.0) (10 3900.0 7760.0) (10 4900.0 7760.0) (10 4900.0 4900.0) (-3 ("23HG_CAD" (1000 . "05/thang/ST1/0/bao") (1000 . "05")))))
  (hg23:em "05/thang/ST1/0/bac/1" '((0 . "LINE") (8 . "KT-THANG") (10 3900.0 5160.0 0.0) (11 4900.0 5160.0 0.0) (-3 ("23HG_CAD" (1000 . "05/thang/ST1/0/bac/1") (1000 . "05")))))
  (hg23:em "05/thang/ST1/0/bac/2" '((0 . "LINE") (8 . "KT-THANG") (10 3900.0 5420.0 0.0) (11 4900.0 5420.0 0.0) (-3 ("23HG_CAD" (1000 . "05/thang/ST1/0/bac/2") (1000 . "05")))))
  (hg23:em "05/thang/ST1/0/bac/3" '((0 . "LINE") (8 . "KT-THANG") (10 3900.0 5680.0 0.0) (11 4900.0 5680.0 0.0) (-3 ("23HG_CAD" (1000 . "05/thang/ST1/0/bac/3") (1000 . "05")))))
  (hg23:em "05/thang/ST1/0/bac/4" '((0 . "LINE") (8 . "KT-THANG") (10 3900.0 5940.0 0.0) (11 4900.0 5940.0 0.0) (-3 ("23HG_CAD" (1000 . "05/thang/ST1/0/bac/4") (1000 . "05")))))
  (hg23:em "05/thang/ST1/0/bac/5" '((0 . "LINE") (8 . "KT-THANG") (10 3900.0 6200.0 0.0) (11 4900.0 6200.0 0.0) (-3 ("23HG_CAD" (1000 . "05/thang/ST1/0/bac/5") (1000 . "05")))))
  (hg23:em "05/thang/ST1/0/bac/6" '((0 . "LINE") (8 . "KT-THANG") (10 3900.0 6460.0 0.0) (11 4900.0 6460.0 0.0) (-3 ("23HG_CAD" (1000 . "05/thang/ST1/0/bac/6") (1000 . "05")))))
  (hg23:em "05/thang/ST1/0/bac/7" '((0 . "LINE") (8 . "KT-THANG") (10 3900.0 6720.0 0.0) (11 4900.0 6720.0 0.0) (-3 ("23HG_CAD" (1000 . "05/thang/ST1/0/bac/7") (1000 . "05")))))
  (hg23:em "05/thang/ST1/0/bac/8" '((0 . "LINE") (8 . "KT-THANG") (10 3900.0 6980.0 0.0) (11 4900.0 6980.0 0.0) (-3 ("23HG_CAD" (1000 . "05/thang/ST1/0/bac/8") (1000 . "05")))))
  (hg23:em "05/thang/ST1/0/bac/9" '((0 . "LINE") (8 . "KT-THANG") (10 3900.0 7240.0 0.0) (11 4900.0 7240.0 0.0) (-3 ("23HG_CAD" (1000 . "05/thang/ST1/0/bac/9") (1000 . "05")))))
  (hg23:em "05/thang/ST1/0/bac/10" '((0 . "LINE") (8 . "KT-THANG") (10 3900.0 7500.0 0.0) (11 4900.0 7500.0 0.0) (-3 ("23HG_CAD" (1000 . "05/thang/ST1/0/bac/10") (1000 . "05")))))
  (hg23:em "05/thang/ST1/0/duong_di" '((0 . "LWPOLYLINE") (100 . "AcDbEntity") (8 . "KT-THANG") (100 . "AcDbPolyline") (90 . 2) (70 . 0) (10 4400.0 5030.0) (10 4400.0 7630.0) (-3 ("23HG_CAD" (1000 . "05/thang/ST1/0/duong_di") (1000 . "05")))))
  (hg23:em "05/thang/ST1/0/mui_ten" '((0 . "LWPOLYLINE") (100 . "AcDbEntity") (8 . "KT-THANG") (100 . "AcDbPolyline") (90 . 3) (70 . 1) (10 4400.0 7630.0) (10 4483.333333 7380.0) (10 4316.666667 7380.0) (-3 ("23HG_CAD" (1000 . "05/thang/ST1/0/mui_ten") (1000 . "05")))))
  (hg23:em "05/thang/ST1/cat" '((0 . "LWPOLYLINE") (100 . "AcDbEntity") (8 . "KT-THANG") (100 . "AcDbPolyline") (90 . 6) (70 . 0) (10 3900.0 6327.324865) (10 4335.048095 6578.5) (10 4415.849365 6538.548095) (10 4384.150635 6693.451905) (10 4464.951905 6653.5) (10 4900.0 6904.675135) (-3 ("23HG_CAD" (1000 . "05/thang/ST1/cat") (1000 . "05")))))
  (hg23:em "05/thang/ST1/chu" '((0 . "TEXT") (8 . "KT-THANG") (7 . "VN_ARIAL") (10 4400.0 4675.0 0.0) (11 4400.0 4675.0 0.0) (40 . 250.0) (1 . "L\U+00CAN") (50 . 0.0) (72 . 1) (73 . 2) (-3 ("23HG_CAD" (1000 . "05/thang/ST1/chu") (1000 . "05")))))
  (hg23:em "06/noi_that/F1" '((0 . "INSERT") (2 . "GIUONG_DOI") (8 . "KT-NOI-THAT") (10 1000.0 6250.0 0.0) (41 . 1.0) (42 . 1.0) (43 . 1.0) (50 . 0.0) (-3 ("23HG_CAD" (1000 . "06/noi_that/F1") (1000 . "06")))))
  (hg23:em "06/noi_that/F2" '((0 . "INSERT") (2 . "TU_AO") (8 . "KT-NOI-THAT") (10 3545.0 6800.0 0.0) (41 . 1.0) (42 . 1.0) (43 . 1.0) (50 . 1.570796326795) (-3 ("23HG_CAD" (1000 . "06/noi_that/F2") (1000 . "06")))))
  (hg23:em "06/noi_that/F3" '((0 . "INSERT") (2 . "SOFA_3") (8 . "KT-NOI-THAT") (10 600.0 3200.0 0.0) (41 . 1.0) (42 . 1.0) (43 . 1.0) (50 . 0.0) (-3 ("23HG_CAD" (1000 . "06/noi_that/F3") (1000 . "06")))))
  (hg23:em "06/noi_that/F4" '((0 . "INSERT") (2 . "BAN_TRA") (8 . "KT-NOI-THAT") (10 1150.0 2200.0 0.0) (41 . 1.0) (42 . 1.0) (43 . 1.0) (50 . 0.0) (-3 ("23HG_CAD" (1000 . "06/noi_that/F4") (1000 . "06")))))
  (hg23:em "06/noi_that/F5" '((0 . "INSERT") (2 . "BAN_AN_4") (8 . "KT-NOI-THAT") (10 8300.0 1500.0 0.0) (41 . 1.0) (42 . 1.0) (43 . 1.0) (50 . 0.0) (-3 ("23HG_CAD" (1000 . "06/noi_that/F5") (1000 . "06")))))
  (hg23:em "06/noi_that/F6" '((0 . "INSERT") (2 . "TU_BEP") (8 . "KT-NOI-THAT") (10 10690.0 800.0 0.0) (41 . 1.0) (42 . 1.0) (43 . 1.0) (50 . 1.570796326795) (-3 ("23HG_CAD" (1000 . "06/noi_that/F6") (1000 . "06")))))
  (hg23:em "06/noi_that/F7" '((0 . "INSERT") (2 . "BON_CAU") (8 . "KT-NOI-THAT") (10 10690.0 5300.0 0.0) (41 . 1.0) (42 . 1.0) (43 . 1.0) (50 . 1.570796326795) (-3 ("23HG_CAD" (1000 . "06/noi_that/F7") (1000 . "06")))))
  (hg23:em "06/noi_that/F8" '((0 . "INSERT") (2 . "LAVABO") (8 . "KT-NOI-THAT") (10 8800.0 4255.0 0.0) (41 . 1.0) (42 . 1.0) (43 . 1.0) (50 . 0.0) (-3 ("23HG_CAD" (1000 . "06/noi_that/F8") (1000 . "06")))))
  (hg23:try "07/hatch/cot/C-1A" 'hg23:hatch1 (list "07/hatch/cot/C-1A" "07" "KT-HATCH" "SOLID" 1.0 0.0 nil nil nil '(((-110.0 -110.0) (110.0 -110.0) (110.0 110.0) (-110.0 110.0)))))
  (hg23:try "07/hatch/cot/C-2A" 'hg23:hatch1 (list "07/hatch/cot/C-2A" "07" "KT-HATCH" "SOLID" 1.0 0.0 nil nil nil '(((3490.0 -110.0) (3710.0 -110.0) (3710.0 110.0) (3490.0 110.0)))))
  (hg23:try "07/hatch/cot/C-3A" 'hg23:hatch1 (list "07/hatch/cot/C-3A" "07" "KT-HATCH" "SOLID" 1.0 0.0 nil nil nil '(((7090.0 -110.0) (7310.0 -110.0) (7310.0 110.0) (7090.0 110.0)))))
  (hg23:try "07/hatch/cot/C-4A" 'hg23:hatch1 (list "07/hatch/cot/C-4A" "07" "KT-HATCH" "SOLID" 1.0 0.0 nil nil nil '(((10690.0 -110.0) (10910.0 -110.0) (10910.0 110.0) (10690.0 110.0)))))
  (hg23:try "07/hatch/cot/C-1B" 'hg23:hatch1 (list "07/hatch/cot/C-1B" "07" "KT-HATCH" "SOLID" 1.0 0.0 nil nil nil '(((-110.0 4090.0) (110.0 4090.0) (110.0 4310.0) (-110.0 4310.0)))))
  (hg23:try "07/hatch/cot/C-2B" 'hg23:hatch1 (list "07/hatch/cot/C-2B" "07" "KT-HATCH" "SOLID" 1.0 0.0 nil nil nil '(((3490.0 4090.0) (3710.0 4090.0) (3710.0 4310.0) (3490.0 4310.0)))))
  (hg23:try "07/hatch/cot/C-3B" 'hg23:hatch1 (list "07/hatch/cot/C-3B" "07" "KT-HATCH" "SOLID" 1.0 0.0 nil nil nil '(((7090.0 4090.0) (7310.0 4090.0) (7310.0 4310.0) (7090.0 4310.0)))))
  (hg23:try "07/hatch/cot/C-4B" 'hg23:hatch1 (list "07/hatch/cot/C-4B" "07" "KT-HATCH" "SOLID" 1.0 0.0 nil nil nil '(((10690.0 4090.0) (10910.0 4090.0) (10910.0 4310.0) (10690.0 4310.0)))))
  (hg23:try "07/hatch/cot/C-1C" 'hg23:hatch1 (list "07/hatch/cot/C-1C" "07" "KT-HATCH" "SOLID" 1.0 0.0 nil nil nil '(((-110.0 8290.0) (110.0 8290.0) (110.0 8510.0) (-110.0 8510.0)))))
  (hg23:try "07/hatch/cot/C-2C" 'hg23:hatch1 (list "07/hatch/cot/C-2C" "07" "KT-HATCH" "SOLID" 1.0 0.0 nil nil nil '(((3490.0 8290.0) (3710.0 8290.0) (3710.0 8510.0) (3490.0 8510.0)))))
  (hg23:try "07/hatch/cot/C-3C" 'hg23:hatch1 (list "07/hatch/cot/C-3C" "07" "KT-HATCH" "SOLID" 1.0 0.0 nil nil nil '(((7090.0 8290.0) (7310.0 8290.0) (7310.0 8510.0) (7090.0 8510.0)))))
  (hg23:try "07/hatch/cot/C-4C" 'hg23:hatch1 (list "07/hatch/cot/C-4C" "07" "KT-HATCH" "SOLID" 1.0 0.0 nil nil nil '(((10690.0 8290.0) (10910.0 8290.0) (10910.0 8510.0) (10690.0 8510.0)))))
  (hg23:try "07/hatch/tuong/xay/0" 'hg23:hatch1 (list "07/hatch/tuong/xay/0" "07" "KT-HATCH" "ANSI31" 31.496063 0.0 nil nil nil '(((-110.0 4090.0) (-110.0 110.0) (110.0 110.0) (110.0 4090.0)))))
  (hg23:try "07/hatch/tuong/xay/1" 'hg23:hatch1 (list "07/hatch/tuong/xay/1" "07" "KT-HATCH" "ANSI31" 31.496063 0.0 nil nil nil '(((-110.0 5700.0) (-110.0 4310.0) (110.0 4310.0) (110.0 5700.0)))))
  (princ))

(defun hg23:ve-2 ()
  (hg23:try "07/hatch/tuong/xay/2" 'hg23:hatch1 (list "07/hatch/tuong/xay/2" "07" "KT-HATCH" "ANSI31" 31.496063 0.0 nil nil nil '(((110.0 6900.0) (110.0 8290.0) (-110.0 8290.0) (-110.0 6900.0)))))
  (hg23:try "07/hatch/tuong/xay/3" 'hg23:hatch1 (list "07/hatch/tuong/xay/3" "07" "KT-HATCH" "ANSI31" 31.496063 0.0 nil nil nil '(((1000.0 110.0) (110.0 110.0) (110.0 -110.0) (1000.0 -110.0)))))
  (hg23:try "07/hatch/tuong/xay/4" 'hg23:hatch1 (list "07/hatch/tuong/xay/4" "07" "KT-HATCH" "ANSI31" 31.496063 0.0 nil nil nil '(((2400.0 4255.0) (110.0 4255.0) (110.0 4145.0) (2400.0 4145.0)))))
  (hg23:try "07/hatch/tuong/xay/5" 'hg23:hatch1 (list "07/hatch/tuong/xay/5" "07" "KT-HATCH" "ANSI31" 31.496063 0.0 nil nil nil '(((110.0 8290.0) (3490.0 8290.0) (3490.0 8510.0) (110.0 8510.0)))))
  (hg23:try "07/hatch/tuong/xay/6" 'hg23:hatch1 (list "07/hatch/tuong/xay/6" "07" "KT-HATCH" "ANSI31" 31.496063 0.0 nil nil nil '(((2600.0 -110.0) (3490.0 -110.0) (3490.0 110.0) (2600.0 110.0)))))
  (hg23:try "07/hatch/tuong/xay/7" 'hg23:hatch1 (list "07/hatch/tuong/xay/7" "07" "KT-HATCH" "ANSI31" 31.496063 0.0 nil nil nil '(((3300.0 4145.0) (3490.0 4145.0) (3490.0 4255.0) (3300.0 4255.0)))))
  (hg23:try "07/hatch/tuong/xay/8" 'hg23:hatch1 (list "07/hatch/tuong/xay/8" "07" "KT-HATCH" "ANSI31" 31.496063 0.0 nil nil nil '(((3545.0 8290.0) (3545.0 4310.0) (3655.0 4310.0) (3655.0 8290.0)))))
  (hg23:try "07/hatch/tuong/xay/9" 'hg23:hatch1 (list "07/hatch/tuong/xay/9" "07" "KT-HATCH" "ANSI31" 31.496063 0.0 nil nil nil '(((4600.0 -110.0) (4600.0 110.0) (3710.0 110.0) (3710.0 -110.0)))))
  (hg23:try "07/hatch/tuong/xay/10" 'hg23:hatch1 (list "07/hatch/tuong/xay/10" "07" "KT-HATCH" "ANSI31" 31.496063 0.0 nil nil nil '(((4800.0 8510.0) (3710.0 8510.0) (3710.0 8290.0) (4800.0 8290.0)))))
  (hg23:try "07/hatch/tuong/xay/11" 'hg23:hatch1 (list "07/hatch/tuong/xay/11" "07" "KT-HATCH" "ANSI31" 31.496063 0.0 nil nil nil '(((6000.0 8290.0) (7090.0 8290.0) (7090.0 8510.0) (6000.0 8510.0)))))
  (hg23:try "07/hatch/tuong/xay/12" 'hg23:hatch1 (list "07/hatch/tuong/xay/12" "07" "KT-HATCH" "ANSI31" 31.496063 0.0 nil nil nil '(((6400.0 -110.0) (7090.0 -110.0) (7090.0 110.0) (6400.0 110.0)))))
  (hg23:try "07/hatch/tuong/xay/13" 'hg23:hatch1 (list "07/hatch/tuong/xay/13" "07" "KT-HATCH" "ANSI31" 31.496063 0.0 nil nil nil '(((7145.0 4800.0) (7145.0 4310.0) (7255.0 4310.0) (7255.0 4800.0)))))
  (hg23:try "07/hatch/tuong/xay/14" 'hg23:hatch1 (list "07/hatch/tuong/xay/14" "07" "KT-HATCH" "ANSI31" 31.496063 0.0 nil nil nil '(((10690.0 6145.0) (10690.0 4310.0) (10910.0 4310.0) (10910.0 6145.0) (10910.0 6255.0) (10910.0 8290.0) (10690.0 8290.0) (10690.0 6255.0) (7255.0 6255.0) (7255.0 6800.0) (7145.0 6800.0) (7145.0 6255.0) (7145.0 6145.0) (7145.0 5500.0) (7255.0 5500.0) (7255.0 6145.0)))))
  (hg23:try "07/hatch/tuong/xay/15" 'hg23:hatch1 (list "07/hatch/tuong/xay/15" "07" "KT-HATCH" "ANSI31" 31.496063 0.0 nil nil nil '(((7255.0 7700.0) (7255.0 8290.0) (7145.0 8290.0) (7145.0 7700.0)))))
  (hg23:try "07/hatch/tuong/xay/16" 'hg23:hatch1 (list "07/hatch/tuong/xay/16" "07" "KT-HATCH" "ANSI31" 31.496063 0.0 nil nil nil '(((8100.0 -110.0) (8100.0 110.0) (7310.0 110.0) (7310.0 -110.0)))))
  (hg23:try "07/hatch/tuong/xay/17" 'hg23:hatch1 (list "07/hatch/tuong/xay/17" "07" "KT-HATCH" "ANSI31" 31.496063 0.0 nil nil nil '(((10690.0 4255.0) (7310.0 4255.0) (7310.0 4145.0) (10690.0 4145.0)))))
  (hg23:try "07/hatch/tuong/xay/18" 'hg23:hatch1 (list "07/hatch/tuong/xay/18" "07" "KT-HATCH" "ANSI31" 31.496063 0.0 nil nil nil '(((7310.0 8290.0) (10690.0 8290.0) (10690.0 8510.0) (7310.0 8510.0)))))
  (hg23:try "07/hatch/tuong/xay/19" 'hg23:hatch1 (list "07/hatch/tuong/xay/19" "07" "KT-HATCH" "ANSI31" 31.496063 0.0 nil nil nil '(((9600.0 -110.0) (10690.0 -110.0) (10690.0 110.0) (9600.0 110.0)))))
  (hg23:try "07/hatch/tuong/xay/20" 'hg23:hatch1 (list "07/hatch/tuong/xay/20" "07" "KT-HATCH" "ANSI31" 31.496063 0.0 nil nil nil '(((10910.0 110.0) (10910.0 4090.0) (10690.0 4090.0) (10690.0 110.0)))))
  (hg23:try "07/hatch/san/P1/0" 'hg23:hatch1 (list "07/hatch/san/P1/0" "07" "KT-HATCH" "NET" 188.976378 0.0 nil nil nil '(((7200.0 110.0) (7200.0 4090.0) (7090.0 4090.0) (7090.0 4200.0) (3710.0 4200.0) (3710.0 4090.0) (3490.0 4090.0) (3490.0 4145.0) (110.0 4145.0) (110.0 4090.0) (110.0 110.0) (3490.0 110.0) (3710.0 110.0) (7090.0 110.0)) ((2150.0 2800.0) (2150.0 2200.0) (1150.0 2200.0) (1150.0 2800.0)) ((2700.0 3200.0) (600.0 3200.0) (600.0 4050.0) (2700.0 4050.0)))))
  (hg23:try "07/hatch/san/P2/0" 'hg23:hatch1 (list "07/hatch/san/P2/0" "07" "KT-HATCH" "NET" 188.976378 0.0 nil nil nil '(((7200.0 4090.0) (7200.0 110.0) (7310.0 110.0) (10690.0 110.0) (10690.0 800.0) (10090.0 800.0) (10090.0 3200.0) (10690.0 3200.0) (10690.0 4090.0) (10690.0 4145.0) (7310.0 4145.0) (7310.0 4090.0)) ((9500.0 1500.0) (8300.0 1500.0) (8300.0 3100.0) (9500.0 3100.0)))))
  (hg23:try "07/hatch/san/P3/0" 'hg23:hatch1 (list "07/hatch/san/P3/0" "07" "KT-HATCH" "LINE" 47.244094 0.0 nil nil nil '(((110.0 4310.0) (110.0 4255.0) (3490.0 4255.0) (3490.0 4310.0) (3545.0 4310.0) (3545.0 6800.0) (2945.0 6800.0) (2945.0 8000.0) (3545.0 8000.0) (3545.0 8290.0) (3490.0 8290.0) (110.0 8290.0)) ((2600.0 6250.0) (1000.0 6250.0) (1000.0 8250.0) (2600.0 8250.0)))))
  (hg23:try "07/hatch/san/P4/0" 'hg23:hatch1 (list "07/hatch/san/P4/0" "07" "KT-HATCH" "NET" 188.976378 0.0 nil nil nil '(((3710.0 4200.0) (7090.0 4200.0) (7090.0 4310.0) (7145.0 4310.0) (7145.0 6145.0) (7145.0 6255.0) (7145.0 8290.0) (7090.0 8290.0) (3710.0 8290.0) (3655.0 8290.0) (3655.0 4310.0) (3710.0 4310.0)) ((3900.0 4900.0) (3900.0 7760.0) (4900.0 7760.0) (4900.0 4900.0)))))
  (hg23:try "07/hatch/san/P5/0" 'hg23:hatch1 (list "07/hatch/san/P5/0" "07" "KT-HATCH" "NET" 94.488189 0.0 nil nil nil '(((8800.0 4255.0) (8800.0 4655.0) (9300.0 4655.0) (9300.0 4255.0) (10690.0 4255.0) (10690.0 4310.0) (10690.0 5300.0) (9990.0 5300.0) (9990.0 5700.0) (10690.0 5700.0) (10690.0 6145.0) (7255.0 6145.0) (7255.0 4310.0) (7310.0 4310.0) (7310.0 4255.0)))))
  (hg23:try "07/hatch/san/P6/0" 'hg23:hatch1 (list "07/hatch/san/P6/0" "07" "KT-HATCH" "NET" 188.976378 0.0 nil nil nil '(((10690.0 8290.0) (7310.0 8290.0) (7255.0 8290.0) (7255.0 6255.0) (10690.0 6255.0)))))
  (hg23:try "08/dim/L2/duoi/0" 'hg23:dim1 (list "08/dim/L2/duoi/0" "08" "KT-DIM" "TCVN_KT_100" '(0.0 0.0 0.0) '(3600.0 0.0 0.0) '(1800.0 -2000.0 0.0) 0.0 nil nil nil nil))
  (hg23:try "08/dim/L2/duoi/1" 'hg23:dim1 (list "08/dim/L2/duoi/1" "08" "KT-DIM" "TCVN_KT_100" '(3600.0 0.0 0.0) '(7200.0 0.0 0.0) '(5400.0 -2000.0 0.0) 0.0 nil nil nil nil))
  (hg23:try "08/dim/L2/duoi/2" 'hg23:dim1 (list "08/dim/L2/duoi/2" "08" "KT-DIM" "TCVN_KT_100" '(7200.0 0.0 0.0) '(10800.0 0.0 0.0) '(9000.0 -2000.0 0.0) 0.0 nil nil nil nil))
  (hg23:try "08/dim/L3/duoi/0" 'hg23:dim1 (list "08/dim/L3/duoi/0" "08" "KT-DIM" "TCVN_KT_100" '(0.0 0.0 0.0) '(10800.0 0.0 0.0) '(5400.0 -2800.0 0.0) 0.0 nil nil nil nil))
  (hg23:try "08/dim/L1/duoi/0" 'hg23:dim1 (list "08/dim/L1/duoi/0" "08" "KT-DIM" "TCVN_KT_100" '(-110.0 -110.0 0.0) '(0.0 -110.0 0.0) '(-55.0 -1200.0 0.0) 0.0 nil nil nil nil))
  (hg23:try "08/dim/L1/duoi/1" 'hg23:dim1 (list "08/dim/L1/duoi/1" "08" "KT-DIM" "TCVN_KT_100" '(0.0 -110.0 0.0) '(1000.0 -110.0 0.0) '(500.0 -1200.0 0.0) 0.0 nil nil nil nil))
  (hg23:try "08/dim/L1/duoi/2" 'hg23:dim1 (list "08/dim/L1/duoi/2" "08" "KT-DIM" "TCVN_KT_100" '(1000.0 -110.0 0.0) '(2600.0 -110.0 0.0) '(1800.0 -1200.0 0.0) 0.0 nil nil nil nil))
  (hg23:try "08/dim/L1/duoi/3" 'hg23:dim1 (list "08/dim/L1/duoi/3" "08" "KT-DIM" "TCVN_KT_100" '(2600.0 -110.0 0.0) '(3600.0 -110.0 0.0) '(3100.0 -1200.0 0.0) 0.0 nil nil nil nil))
  (hg23:try "08/dim/L1/duoi/4" 'hg23:dim1 (list "08/dim/L1/duoi/4" "08" "KT-DIM" "TCVN_KT_100" '(3600.0 -110.0 0.0) '(4600.0 -110.0 0.0) '(4100.0 -1200.0 0.0) 0.0 nil nil nil nil))
  (hg23:try "08/dim/L1/duoi/5" 'hg23:dim1 (list "08/dim/L1/duoi/5" "08" "KT-DIM" "TCVN_KT_100" '(4600.0 -110.0 0.0) '(6400.0 -110.0 0.0) '(5500.0 -1200.0 0.0) 0.0 nil nil nil nil))
  (hg23:try "08/dim/L1/duoi/6" 'hg23:dim1 (list "08/dim/L1/duoi/6" "08" "KT-DIM" "TCVN_KT_100" '(6400.0 -110.0 0.0) '(7200.0 -110.0 0.0) '(6800.0 -1200.0 0.0) 0.0 nil nil nil nil))
  (hg23:try "08/dim/L1/duoi/7" 'hg23:dim1 (list "08/dim/L1/duoi/7" "08" "KT-DIM" "TCVN_KT_100" '(7200.0 -110.0 0.0) '(8100.0 -110.0 0.0) '(7650.0 -1200.0 0.0) 0.0 nil nil nil nil))
  (hg23:try "08/dim/L1/duoi/8" 'hg23:dim1 (list "08/dim/L1/duoi/8" "08" "KT-DIM" "TCVN_KT_100" '(8100.0 -110.0 0.0) '(9600.0 -110.0 0.0) '(8850.0 -1200.0 0.0) 0.0 nil nil nil nil))
  (hg23:try "08/dim/L1/duoi/9" 'hg23:dim1 (list "08/dim/L1/duoi/9" "08" "KT-DIM" "TCVN_KT_100" '(9600.0 -110.0 0.0) '(10800.0 -110.0 0.0) '(10200.0 -1200.0 0.0) 0.0 nil nil nil nil))
  (hg23:try "08/dim/L1/duoi/10" 'hg23:dim1 (list "08/dim/L1/duoi/10" "08" "KT-DIM" "TCVN_KT_100" '(10800.0 -110.0 0.0) '(10910.0 -110.0 0.0) '(10855.0 -1200.0 0.0) 0.0 nil nil nil nil))
  (hg23:try "08/dim/L2/tren/0" 'hg23:dim1 (list "08/dim/L2/tren/0" "08" "KT-DIM" "TCVN_KT_100" '(0.0 8400.0 0.0) '(3600.0 8400.0 0.0) '(1800.0 10400.0 0.0) 0.0 nil nil nil nil))
  (hg23:try "08/dim/L2/tren/1" 'hg23:dim1 (list "08/dim/L2/tren/1" "08" "KT-DIM" "TCVN_KT_100" '(3600.0 8400.0 0.0) '(7200.0 8400.0 0.0) '(5400.0 10400.0 0.0) 0.0 nil nil nil nil))
  (hg23:try "08/dim/L2/tren/2" 'hg23:dim1 (list "08/dim/L2/tren/2" "08" "KT-DIM" "TCVN_KT_100" '(7200.0 8400.0 0.0) '(10800.0 8400.0 0.0) '(9000.0 10400.0 0.0) 0.0 nil nil nil nil))
  (hg23:try "08/dim/L3/tren/0" 'hg23:dim1 (list "08/dim/L3/tren/0" "08" "KT-DIM" "TCVN_KT_100" '(0.0 8400.0 0.0) '(10800.0 8400.0 0.0) '(5400.0 11200.0 0.0) 0.0 nil nil nil nil))
  (hg23:try "08/dim/L1/tren/0" 'hg23:dim1 (list "08/dim/L1/tren/0" "08" "KT-DIM" "TCVN_KT_100" '(-110.0 8510.0 0.0) '(0.0 8510.0 0.0) '(-55.0 9600.0 0.0) 0.0 nil nil nil nil))
  (hg23:try "08/dim/L1/tren/1" 'hg23:dim1 (list "08/dim/L1/tren/1" "08" "KT-DIM" "TCVN_KT_100" '(0.0 8510.0 0.0) '(3600.0 8510.0 0.0) '(1800.0 9600.0 0.0) 0.0 nil nil nil nil))
  (hg23:try "08/dim/L1/tren/2" 'hg23:dim1 (list "08/dim/L1/tren/2" "08" "KT-DIM" "TCVN_KT_100" '(3600.0 8510.0 0.0) '(4800.0 8510.0 0.0) '(4200.0 9600.0 0.0) 0.0 nil nil nil nil))
  (hg23:try "08/dim/L1/tren/3" 'hg23:dim1 (list "08/dim/L1/tren/3" "08" "KT-DIM" "TCVN_KT_100" '(4800.0 8510.0 0.0) '(6000.0 8510.0 0.0) '(5400.0 9600.0 0.0) 0.0 nil nil nil nil))
  (hg23:try "08/dim/L1/tren/4" 'hg23:dim1 (list "08/dim/L1/tren/4" "08" "KT-DIM" "TCVN_KT_100" '(6000.0 8510.0 0.0) '(7200.0 8510.0 0.0) '(6600.0 9600.0 0.0) 0.0 nil nil nil nil))
  (hg23:try "08/dim/L1/tren/5" 'hg23:dim1 (list "08/dim/L1/tren/5" "08" "KT-DIM" "TCVN_KT_100" '(7200.0 8510.0 0.0) '(10800.0 8510.0 0.0) '(9000.0 9600.0 0.0) 0.0 nil nil nil nil))
  (hg23:try "08/dim/L1/tren/6" 'hg23:dim1 (list "08/dim/L1/tren/6" "08" "KT-DIM" "TCVN_KT_100" '(10800.0 8510.0 0.0) '(10910.0 8510.0 0.0) '(10855.0 9600.0 0.0) 0.0 nil nil nil nil))
  (hg23:try "08/dim/L2/trai/0" 'hg23:dim1 (list "08/dim/L2/trai/0" "08" "KT-DIM" "TCVN_KT_100" '(0.0 0.0 0.0) '(0.0 4200.0 0.0) '(-2000.0 2100.0 0.0) 1.570796326795 nil nil nil nil))
  (hg23:try "08/dim/L2/trai/1" 'hg23:dim1 (list "08/dim/L2/trai/1" "08" "KT-DIM" "TCVN_KT_100" '(0.0 4200.0 0.0) '(0.0 8400.0 0.0) '(-2000.0 6300.0 0.0) 1.570796326795 nil nil nil nil))
  (hg23:try "08/dim/L3/trai/0" 'hg23:dim1 (list "08/dim/L3/trai/0" "08" "KT-DIM" "TCVN_KT_100" '(0.0 0.0 0.0) '(0.0 8400.0 0.0) '(-2800.0 4200.0 0.0) 1.570796326795 nil nil nil nil))
  (hg23:try "08/dim/L1/trai/0" 'hg23:dim1 (list "08/dim/L1/trai/0" "08" "KT-DIM" "TCVN_KT_100" '(-110.0 -110.0 0.0) '(-110.0 0.0 0.0) '(-1200.0 -55.0 0.0) 1.570796326795 nil nil nil nil))
  (hg23:try "08/dim/L1/trai/1" 'hg23:dim1 (list "08/dim/L1/trai/1" "08" "KT-DIM" "TCVN_KT_100" '(-110.0 0.0 0.0) '(-110.0 4200.0 0.0) '(-1200.0 2100.0 0.0) 1.570796326795 nil nil nil nil))
  (hg23:try "08/dim/L1/trai/2" 'hg23:dim1 (list "08/dim/L1/trai/2" "08" "KT-DIM" "TCVN_KT_100" '(-110.0 4200.0 0.0) '(-110.0 5700.0 0.0) '(-1200.0 4950.0 0.0) 1.570796326795 nil nil nil nil))
  (hg23:try "08/dim/L1/trai/3" 'hg23:dim1 (list "08/dim/L1/trai/3" "08" "KT-DIM" "TCVN_KT_100" '(-110.0 5700.0 0.0) '(-110.0 6900.0 0.0) '(-1200.0 6300.0 0.0) 1.570796326795 nil nil nil nil))
  (hg23:try "08/dim/L1/trai/4" 'hg23:dim1 (list "08/dim/L1/trai/4" "08" "KT-DIM" "TCVN_KT_100" '(-110.0 6900.0 0.0) '(-110.0 8400.0 0.0) '(-1200.0 7650.0 0.0) 1.570796326795 nil nil nil nil))
  (hg23:try "08/dim/L1/trai/5" 'hg23:dim1 (list "08/dim/L1/trai/5" "08" "KT-DIM" "TCVN_KT_100" '(-110.0 8400.0 0.0) '(-110.0 8510.0 0.0) '(-1200.0 8455.0 0.0) 1.570796326795 nil nil nil nil))
  (hg23:try "08/dim/L2/phai/0" 'hg23:dim1 (list "08/dim/L2/phai/0" "08" "KT-DIM" "TCVN_KT_100" '(10800.0 0.0 0.0) '(10800.0 4200.0 0.0) '(12800.0 2100.0 0.0) 1.570796326795 nil nil nil nil))
  (hg23:try "08/dim/L2/phai/1" 'hg23:dim1 (list "08/dim/L2/phai/1" "08" "KT-DIM" "TCVN_KT_100" '(10800.0 4200.0 0.0) '(10800.0 8400.0 0.0) '(12800.0 6300.0 0.0) 1.570796326795 nil nil nil nil))
  (hg23:try "08/dim/L3/phai/0" 'hg23:dim1 (list "08/dim/L3/phai/0" "08" "KT-DIM" "TCVN_KT_100" '(10800.0 0.0 0.0) '(10800.0 8400.0 0.0) '(13600.0 4200.0 0.0) 1.570796326795 nil nil nil nil))
  (hg23:try "08/dim/L1/phai/0" 'hg23:dim1 (list "08/dim/L1/phai/0" "08" "KT-DIM" "TCVN_KT_100" '(10910.0 -110.0 0.0) '(10910.0 0.0 0.0) '(12000.0 -55.0 0.0) 1.570796326795 nil nil nil nil))
  (hg23:try "08/dim/L1/phai/1" 'hg23:dim1 (list "08/dim/L1/phai/1" "08" "KT-DIM" "TCVN_KT_100" '(10910.0 0.0 0.0) '(10910.0 4200.0 0.0) '(12000.0 2100.0 0.0) 1.570796326795 nil nil nil nil))
  (hg23:try "08/dim/L1/phai/2" 'hg23:dim1 (list "08/dim/L1/phai/2" "08" "KT-DIM" "TCVN_KT_100" '(10910.0 4200.0 0.0) '(10910.0 8400.0 0.0) '(12000.0 6300.0 0.0) 1.570796326795 nil nil nil nil))
  (hg23:try "08/dim/L1/phai/3" 'hg23:dim1 (list "08/dim/L1/phai/3" "08" "KT-DIM" "TCVN_KT_100" '(10910.0 8400.0 0.0) '(10910.0 8510.0 0.0) '(12000.0 8455.0 0.0) 1.570796326795 nil nil nil nil))
  (hg23:em "09/hoan_thien/P1/ten" '((0 . "TEXT") (8 . "KT-HOAN-THIEN") (7 . "VN_ARIAL") (10 3931.225775 2409.039525 0.0) (11 3931.225775 2409.039525 0.0) (40 . 300.0) (1 . "PH\U+00D2NG KH\U+00C1CH") (50 . 0.0) (72 . 1) (73 . 2) (-3 ("23HG_CAD" (1000 . "09/hoan_thien/P1/ten") (1000 . "09")))))
  (hg23:em "09/hoan_thien/P1/dien_tich" '((0 . "TEXT") (8 . "KT-HOAN-THIEN") (7 . "VN_ARIAL") (10 3931.225775 2049.039525 0.0) (11 3931.225775 2049.039525 0.0) (40 . 220.0) (1 . "S = 30,24 m\U+00B2") (50 . 0.0) (72 . 1) (73 . 2) (-3 ("23HG_CAD" (1000 . "09/hoan_thien/P1/dien_tich") (1000 . "09")))))
  (hg23:em "09/hoan_thien/P1/cote" '((0 . "TEXT") (8 . "KT-HOAN-THIEN") (7 . "VN_ARIAL") (10 3931.225775 1729.039525 0.0) (11 3931.225775 1729.039525 0.0) (40 . 220.0) (1 . "\U+00B10.000") (50 . 0.0) (72 . 1) (73 . 2) (-3 ("23HG_CAD" (1000 . "09/hoan_thien/P1/cote") (1000 . "09")))))
  (hg23:em "09/hoan_thien/P2/ten" '((0 . "TEXT") (8 . "KT-HOAN-THIEN") (7 . "VN_ARIAL") (10 8799.583333 1102.5 0.0) (11 8799.583333 1102.5 0.0) (40 . 300.0) (1 . "B\U+1EBEP + \U+0102N") (50 . 0.0) (72 . 1) (73 . 2) (-3 ("23HG_CAD" (1000 . "09/hoan_thien/P2/ten") (1000 . "09")))))
  (hg23:em "09/hoan_thien/P2/dien_tich" '((0 . "TEXT") (8 . "KT-HOAN-THIEN") (7 . "VN_ARIAL") (10 8799.583333 742.5 0.0) (11 8799.583333 742.5 0.0) (40 . 220.0) (1 . "S = 15,12 m\U+00B2") (50 . 0.0) (72 . 1) (73 . 2) (-3 ("23HG_CAD" (1000 . "09/hoan_thien/P2/dien_tich") (1000 . "09")))))
  (hg23:em "09/hoan_thien/P2/cote" '((0 . "TEXT") (8 . "KT-HOAN-THIEN") (7 . "VN_ARIAL") (10 8799.583333 422.5 0.0) (11 8799.583333 422.5 0.0) (40 . 220.0) (1 . "\U+00B10.000") (50 . 0.0) (72 . 1) (73 . 2) (-3 ("23HG_CAD" (1000 . "09/hoan_thien/P2/cote") (1000 . "09")))))
  (hg23:em "09/hoan_thien/P3/ten" '((0 . "TEXT") (8 . "KT-HOAN-THIEN") (7 . "VN_ARIAL") (10 1684.375 5920.0 0.0) (11 1684.375 5920.0 0.0) (40 . 300.0) (1 . "PH\U+00D2NG NG\U+1EE6") (50 . 0.0) (72 . 1) (73 . 2) (-3 ("23HG_CAD" (1000 . "09/hoan_thien/P3/ten") (1000 . "09")))))
  (hg23:em "09/hoan_thien/P3/dien_tich" '((0 . "TEXT") (8 . "KT-HOAN-THIEN") (7 . "VN_ARIAL") (10 1684.375 5560.0 0.0) (11 1684.375 5560.0 0.0) (40 . 220.0) (1 . "S = 15,12 m\U+00B2") (50 . 0.0) (72 . 1) (73 . 2) (-3 ("23HG_CAD" (1000 . "09/hoan_thien/P3/dien_tich") (1000 . "09")))))
  (hg23:em "09/hoan_thien/P3/cote" '((0 . "TEXT") (8 . "KT-HOAN-THIEN") (7 . "VN_ARIAL") (10 1684.375 5240.0 0.0) (11 1684.375 5240.0 0.0) (40 . 220.0) (1 . "\U+00B10.000") (50 . 0.0) (72 . 1) (73 . 2) (-3 ("23HG_CAD" (1000 . "09/hoan_thien/P3/cote") (1000 . "09")))))
  (hg23:em "09/hoan_thien/P4/ten" '((0 . "TEXT") (8 . "KT-HOAN-THIEN") (7 . "VN_ARIAL") (10 5836.25 6565.0 0.0) (11 5836.25 6565.0 0.0) (40 . 300.0) (1 . "S\U+1EA2NH THANG") (50 . 0.0) (72 . 1) (73 . 2) (-3 ("23HG_CAD" (1000 . "09/hoan_thien/P4/ten") (1000 . "09")))))
  (hg23:em "09/hoan_thien/P4/dien_tich" '((0 . "TEXT") (8 . "KT-HOAN-THIEN") (7 . "VN_ARIAL") (10 5836.25 6205.0 0.0) (11 5836.25 6205.0 0.0) (40 . 220.0) (1 . "S = 15,12 m\U+00B2") (50 . 0.0) (72 . 1) (73 . 2) (-3 ("23HG_CAD" (1000 . "09/hoan_thien/P4/dien_tich") (1000 . "09")))))
  (hg23:em "09/hoan_thien/P4/cote" '((0 . "TEXT") (8 . "KT-HOAN-THIEN") (7 . "VN_ARIAL") (10 5836.25 5885.0 0.0) (11 5836.25 5885.0 0.0) (40 . 220.0) (1 . "\U+00B10.000") (50 . 0.0) (72 . 1) (73 . 2) (-3 ("23HG_CAD" (1000 . "09/hoan_thien/P4/cote") (1000 . "09")))))
  (hg23:em "09/hoan_thien/P5/ten" '((0 . "TEXT") (8 . "KT-HOAN-THIEN") (7 . "VN_ARIAL") (10 8972.5 5598.75 0.0) (11 8972.5 5598.75 0.0) (40 . 300.0) (1 . "WC") (50 . 0.0) (72 . 1) (73 . 2) (-3 ("23HG_CAD" (1000 . "09/hoan_thien/P5/ten") (1000 . "09")))))
  (hg23:em "09/hoan_thien/P5/dien_tich" '((0 . "TEXT") (8 . "KT-HOAN-THIEN") (7 . "VN_ARIAL") (10 8972.5 5238.75 0.0) (11 8972.5 5238.75 0.0) (40 . 220.0) (1 . "S = 7,20 m\U+00B2") (50 . 0.0) (72 . 1) (73 . 2) (-3 ("23HG_CAD" (1000 . "09/hoan_thien/P5/dien_tich") (1000 . "09")))))
  (hg23:em "09/hoan_thien/P5/cote" '((0 . "TEXT") (8 . "KT-HOAN-THIEN") (7 . "VN_ARIAL") (10 8972.5 4918.75 0.0) (11 8972.5 4918.75 0.0) (40 . 220.0) (1 . "-0.020") (50 . 0.0) (72 . 1) (73 . 2) (-3 ("23HG_CAD" (1000 . "09/hoan_thien/P5/cote") (1000 . "09")))))
  (hg23:em "09/hoan_thien/P6/ten" '((0 . "TEXT") (8 . "KT-HOAN-THIEN") (7 . "VN_ARIAL") (10 9258.75 7592.5 0.0) (11 9258.75 7592.5 0.0) (40 . 300.0) (1 . "KHO") (50 . 0.0) (72 . 1) (73 . 2) (-3 ("23HG_CAD" (1000 . "09/hoan_thien/P6/ten") (1000 . "09")))))
  (hg23:em "09/hoan_thien/P6/dien_tich" '((0 . "TEXT") (8 . "KT-HOAN-THIEN") (7 . "VN_ARIAL") (10 9258.75 7232.5 0.0) (11 9258.75 7232.5 0.0) (40 . 220.0) (1 . "S = 7,92 m\U+00B2") (50 . 0.0) (72 . 1) (73 . 2) (-3 ("23HG_CAD" (1000 . "09/hoan_thien/P6/dien_tich") (1000 . "09")))))
  (hg23:em "09/hoan_thien/P6/cote" '((0 . "TEXT") (8 . "KT-HOAN-THIEN") (7 . "VN_ARIAL") (10 9258.75 6912.5 0.0) (11 9258.75 6912.5 0.0) (40 . 220.0) (1 . "\U+00B10.000") (50 . 0.0) (72 . 1) (73 . 2) (-3 ("23HG_CAD" (1000 . "09/hoan_thien/P6/cote") (1000 . "09")))))
  (hg23:em "09/hoan_thien/bang/khung" '((0 . "LWPOLYLINE") (100 . "AcDbEntity") (8 . "KT-HOAN-THIEN") (100 . "AcDbPolyline") (90 . 4) (70 . 1) (10 16800.0 4750.0) (10 32400.0 4750.0) (10 32400.0 12200.0) (10 16800.0 12200.0) (-3 ("23HG_CAD" (1000 . "09/hoan_thien/bang/khung") (1000 . "09")))))
  (hg23:em "09/hoan_thien/bang/ke_ngang/1" '((0 . "LINE") (8 . "KT-HOAN-THIEN") (10 16800.0 11550.0 0.0) (11 32400.0 11550.0 0.0) (-3 ("23HG_CAD" (1000 . "09/hoan_thien/bang/ke_ngang/1") (1000 . "09")))))
  (hg23:em "09/hoan_thien/bang/ke_ngang/2" '((0 . "LINE") (8 . "KT-HOAN-THIEN") (10 16800.0 10750.0 0.0) (11 32400.0 10750.0 0.0) (-3 ("23HG_CAD" (1000 . "09/hoan_thien/bang/ke_ngang/2") (1000 . "09")))))
  (hg23:em "09/hoan_thien/bang/ke_ngang/3" '((0 . "LINE") (8 . "KT-HOAN-THIEN") (10 16800.0 9950.0 0.0) (11 32400.0 9950.0 0.0) (-3 ("23HG_CAD" (1000 . "09/hoan_thien/bang/ke_ngang/3") (1000 . "09")))))
  (hg23:em "09/hoan_thien/bang/ke_ngang/4" '((0 . "LINE") (8 . "KT-HOAN-THIEN") (10 16800.0 9150.0 0.0) (11 32400.0 9150.0 0.0) (-3 ("23HG_CAD" (1000 . "09/hoan_thien/bang/ke_ngang/4") (1000 . "09")))))
  (hg23:em "09/hoan_thien/bang/ke_ngang/5" '((0 . "LINE") (8 . "KT-HOAN-THIEN") (10 16800.0 8550.0 0.0) (11 32400.0 8550.0 0.0) (-3 ("23HG_CAD" (1000 . "09/hoan_thien/bang/ke_ngang/5") (1000 . "09")))))
  (hg23:em "09/hoan_thien/bang/ke_ngang/6" '((0 . "LINE") (8 . "KT-HOAN-THIEN") (10 16800.0 7750.0 0.0) (11 32400.0 7750.0 0.0) (-3 ("23HG_CAD" (1000 . "09/hoan_thien/bang/ke_ngang/6") (1000 . "09")))))
  (hg23:em "09/hoan_thien/bang/ke_ngang/7" '((0 . "LINE") (8 . "KT-HOAN-THIEN") (10 16800.0 6950.0 0.0) (11 32400.0 6950.0 0.0) (-3 ("23HG_CAD" (1000 . "09/hoan_thien/bang/ke_ngang/7") (1000 . "09")))))
  (hg23:em "09/hoan_thien/bang/ke_ngang/8" '((0 . "LINE") (8 . "KT-HOAN-THIEN") (10 16800.0 6150.0 0.0) (11 32400.0 6150.0 0.0) (-3 ("23HG_CAD" (1000 . "09/hoan_thien/bang/ke_ngang/8") (1000 . "09")))))
  (hg23:em "09/hoan_thien/bang/ke_ngang/9" '((0 . "LINE") (8 . "KT-HOAN-THIEN") (10 16800.0 5550.0 0.0) (11 32400.0 5550.0 0.0) (-3 ("23HG_CAD" (1000 . "09/hoan_thien/bang/ke_ngang/9") (1000 . "09")))))
  (hg23:em "09/hoan_thien/bang/ke_doc/1/0" '((0 . "LINE") (8 . "KT-HOAN-THIEN") (10 17600.0 11550.0 0.0) (11 17600.0 6150.0 0.0) (-3 ("23HG_CAD" (1000 . "09/hoan_thien/bang/ke_doc/1/0") (1000 . "09")))))
  (hg23:em "09/hoan_thien/bang/ke_doc/2/0" '((0 . "LINE") (8 . "KT-HOAN-THIEN") (10 20000.0 11550.0 0.0) (11 20000.0 5550.0 0.0) (-3 ("23HG_CAD" (1000 . "09/hoan_thien/bang/ke_doc/2/0") (1000 . "09")))))
  (hg23:em "09/hoan_thien/bang/ke_doc/3/0" '((0 . "LINE") (8 . "KT-HOAN-THIEN") (10 21600.0 11550.0 0.0) (11 21600.0 5550.0 0.0) (-3 ("23HG_CAD" (1000 . "09/hoan_thien/bang/ke_doc/3/0") (1000 . "09")))))
  (hg23:em "09/hoan_thien/bang/ke_doc/4/0" '((0 . "LINE") (8 . "KT-HOAN-THIEN") (10 25200.0 11550.0 0.0) (11 25200.0 6150.0 0.0) (-3 ("23HG_CAD" (1000 . "09/hoan_thien/bang/ke_doc/4/0") (1000 . "09")))))
  (hg23:em "09/hoan_thien/bang/ke_doc/5/0" '((0 . "LINE") (8 . "KT-HOAN-THIEN") (10 28400.0 11550.0 0.0) (11 28400.0 6150.0 0.0) (-3 ("23HG_CAD" (1000 . "09/hoan_thien/bang/ke_doc/5/0") (1000 . "09")))))
  (hg23:em "09/hoan_thien/bang/ke_doc/6/0" '((0 . "LINE") (8 . "KT-HOAN-THIEN") (10 31000.0 11550.0 0.0) (11 31000.0 6150.0 0.0) (-3 ("23HG_CAD" (1000 . "09/hoan_thien/bang/ke_doc/6/0") (1000 . "09")))))
  (hg23:em "09/hoan_thien/bang/tieu_de/0" '((0 . "TEXT") (8 . "KT-HOAN-THIEN") (7 . "VN_ARIAL") (10 24600.0 11875.0 0.0) (11 24600.0 11875.0 0.0) (40 . 300.0) (1 . "B\U+1EA2NG HO\U+00C0N THI\U+1EC6N") (50 . 0.0) (72 . 1) (73 . 2) (-3 ("23HG_CAD" (1000 . "09/hoan_thien/bang/tieu_de/0") (1000 . "09")))))
  (hg23:em "09/hoan_thien/bang/cot/0/0" '((0 . "TEXT") (8 . "KT-HOAN-THIEN") (7 . "VN_ARIAL") (10 17200.0 11150.0 0.0) (11 17200.0 11150.0 0.0) (40 . 200.0) (1 . "STT") (50 . 0.0) (72 . 1) (73 . 2) (-3 ("23HG_CAD" (1000 . "09/hoan_thien/bang/cot/0/0") (1000 . "09")))))
  (hg23:em "09/hoan_thien/bang/cot/1/0" '((0 . "TEXT") (8 . "KT-HOAN-THIEN") (7 . "VN_ARIAL") (10 18800.0 11150.0 0.0) (11 18800.0 11150.0 0.0) (40 . 200.0) (1 . "Ph\U+00F2ng") (50 . 0.0) (72 . 1) (73 . 2) (-3 ("23HG_CAD" (1000 . "09/hoan_thien/bang/cot/1/0") (1000 . "09")))))
  (hg23:em "09/hoan_thien/bang/cot/2/0" '((0 . "TEXT") (8 . "KT-HOAN-THIEN") (7 . "VN_ARIAL") (10 20800.0 11300.0 0.0) (11 20800.0 11300.0 0.0) (40 . 200.0) (1 . "Di\U+1EC7n t\U+00EDch") (50 . 0.0) (72 . 1) (73 . 2) (-3 ("23HG_CAD" (1000 . "09/hoan_thien/bang/cot/2/0") (1000 . "09")))))
  (hg23:em "09/hoan_thien/bang/cot/2/1" '((0 . "TEXT") (8 . "KT-HOAN-THIEN") (7 . "VN_ARIAL") (10 20800.0 11000.0 0.0) (11 20800.0 11000.0 0.0) (40 . 200.0) (1 . "(m\U+00B2)") (50 . 0.0) (72 . 1) (73 . 2) (-3 ("23HG_CAD" (1000 . "09/hoan_thien/bang/cot/2/1") (1000 . "09")))))
  (hg23:em "09/hoan_thien/bang/cot/3/0" '((0 . "TEXT") (8 . "KT-HOAN-THIEN") (7 . "VN_ARIAL") (10 23400.0 11150.0 0.0) (11 23400.0 11150.0 0.0) (40 . 200.0) (1 . "S\U+00E0n") (50 . 0.0) (72 . 1) (73 . 2) (-3 ("23HG_CAD" (1000 . "09/hoan_thien/bang/cot/3/0") (1000 . "09")))))
  (hg23:em "09/hoan_thien/bang/cot/4/0" '((0 . "TEXT") (8 . "KT-HOAN-THIEN") (7 . "VN_ARIAL") (10 26800.0 11150.0 0.0) (11 26800.0 11150.0 0.0) (40 . 200.0) (1 . "T\U+01B0\U+1EDDng") (50 . 0.0) (72 . 1) (73 . 2) (-3 ("23HG_CAD" (1000 . "09/hoan_thien/bang/cot/4/0") (1000 . "09")))))
  (hg23:em "09/hoan_thien/bang/cot/5/0" '((0 . "TEXT") (8 . "KT-HOAN-THIEN") (7 . "VN_ARIAL") (10 29700.0 11150.0 0.0) (11 29700.0 11150.0 0.0) (40 . 200.0) (1 . "Tr\U+1EA7n") (50 . 0.0) (72 . 1) (73 . 2) (-3 ("23HG_CAD" (1000 . "09/hoan_thien/bang/cot/5/0") (1000 . "09")))))
  (hg23:em "09/hoan_thien/bang/cot/6/0" '((0 . "TEXT") (8 . "KT-HOAN-THIEN") (7 . "VN_ARIAL") (10 31700.0 11150.0 0.0) (11 31700.0 11150.0 0.0) (40 . 200.0) (1 . "Cote") (50 . 0.0) (72 . 1) (73 . 2) (-3 ("23HG_CAD" (1000 . "09/hoan_thien/bang/cot/6/0") (1000 . "09")))))
  (hg23:em "09/hoan_thien/bang/hang/P1/0/0" '((0 . "TEXT") (8 . "KT-HOAN-THIEN") (7 . "VN_ARIAL") (10 17200.0 10350.0 0.0) (11 17200.0 10350.0 0.0) (40 . 200.0) (1 . "1") (50 . 0.0) (72 . 1) (73 . 2) (-3 ("23HG_CAD" (1000 . "09/hoan_thien/bang/hang/P1/0/0") (1000 . "09")))))
  (hg23:em "09/hoan_thien/bang/hang/P1/1/0" '((0 . "TEXT") (8 . "KT-HOAN-THIEN") (7 . "VN_ARIAL") (10 17700.0 10350.0 0.0) (11 17700.0 10350.0 0.0) (40 . 200.0) (1 . "PH\U+00D2NG KH\U+00C1CH") (50 . 0.0) (72 . 0) (73 . 2) (-3 ("23HG_CAD" (1000 . "09/hoan_thien/bang/hang/P1/1/0") (1000 . "09")))))
  (hg23:em "09/hoan_thien/bang/hang/P1/2/0" '((0 . "TEXT") (8 . "KT-HOAN-THIEN") (7 . "VN_ARIAL") (10 20800.0 10350.0 0.0) (11 20800.0 10350.0 0.0) (40 . 200.0) (1 . "30,24") (50 . 0.0) (72 . 1) (73 . 2) (-3 ("23HG_CAD" (1000 . "09/hoan_thien/bang/hang/P1/2/0") (1000 . "09")))))
  (hg23:em "09/hoan_thien/bang/hang/P1/3/0" '((0 . "TEXT") (8 . "KT-HOAN-THIEN") (7 . "VN_ARIAL") (10 21700.0 10500.0 0.0) (11 21700.0 10500.0 0.0) (40 . 200.0) (1 . "L\U+00E1t g\U+1EA1ch granite") (50 . 0.0) (72 . 0) (73 . 2) (-3 ("23HG_CAD" (1000 . "09/hoan_thien/bang/hang/P1/3/0") (1000 . "09")))))
  (hg23:em "09/hoan_thien/bang/hang/P1/3/1" '((0 . "TEXT") (8 . "KT-HOAN-THIEN") (7 . "VN_ARIAL") (10 21700.0 10200.0 0.0) (11 21700.0 10200.0 0.0) (40 . 200.0) (1 . "600\U+00D7600") (50 . 0.0) (72 . 0) (73 . 2) (-3 ("23HG_CAD" (1000 . "09/hoan_thien/bang/hang/P1/3/1") (1000 . "09")))))
  (hg23:em "09/hoan_thien/bang/hang/P1/4/0" '((0 . "TEXT") (8 . "KT-HOAN-THIEN") (7 . "VN_ARIAL") (10 25300.0 10350.0 0.0) (11 25300.0 10350.0 0.0) (40 . 200.0) (1 . "S\U+01A1n n\U+01B0\U+1EDBc 1 l\U+00F3t 2 ph\U+1EE7") (50 . 0.0) (72 . 0) (73 . 2) (-3 ("23HG_CAD" (1000 . "09/hoan_thien/bang/hang/P1/4/0") (1000 . "09")))))
  (hg23:em "09/hoan_thien/bang/hang/P1/5/0" '((0 . "TEXT") (8 . "KT-HOAN-THIEN") (7 . "VN_ARIAL") (10 28500.0 10350.0 0.0) (11 28500.0 10350.0 0.0) (40 . 200.0) (1 . "Tr\U+1EA7n th\U+1EA1ch cao") (50 . 0.0) (72 . 0) (73 . 2) (-3 ("23HG_CAD" (1000 . "09/hoan_thien/bang/hang/P1/5/0") (1000 . "09")))))
  (hg23:em "09/hoan_thien/bang/hang/P1/6/0" '((0 . "TEXT") (8 . "KT-HOAN-THIEN") (7 . "VN_ARIAL") (10 31700.0 10350.0 0.0) (11 31700.0 10350.0 0.0) (40 . 200.0) (1 . "\U+00B10.000") (50 . 0.0) (72 . 1) (73 . 2) (-3 ("23HG_CAD" (1000 . "09/hoan_thien/bang/hang/P1/6/0") (1000 . "09")))))
  (hg23:em "09/hoan_thien/bang/hang/P2/0/0" '((0 . "TEXT") (8 . "KT-HOAN-THIEN") (7 . "VN_ARIAL") (10 17200.0 9550.0 0.0) (11 17200.0 9550.0 0.0) (40 . 200.0) (1 . "2") (50 . 0.0) (72 . 1) (73 . 2) (-3 ("23HG_CAD" (1000 . "09/hoan_thien/bang/hang/P2/0/0") (1000 . "09")))))
  (hg23:em "09/hoan_thien/bang/hang/P2/1/0" '((0 . "TEXT") (8 . "KT-HOAN-THIEN") (7 . "VN_ARIAL") (10 17700.0 9550.0 0.0) (11 17700.0 9550.0 0.0) (40 . 200.0) (1 . "B\U+1EBEP + \U+0102N") (50 . 0.0) (72 . 0) (73 . 2) (-3 ("23HG_CAD" (1000 . "09/hoan_thien/bang/hang/P2/1/0") (1000 . "09")))))
  (hg23:em "09/hoan_thien/bang/hang/P2/2/0" '((0 . "TEXT") (8 . "KT-HOAN-THIEN") (7 . "VN_ARIAL") (10 20800.0 9550.0 0.0) (11 20800.0 9550.0 0.0) (40 . 200.0) (1 . "15,12") (50 . 0.0) (72 . 1) (73 . 2) (-3 ("23HG_CAD" (1000 . "09/hoan_thien/bang/hang/P2/2/0") (1000 . "09")))))
  (hg23:em "09/hoan_thien/bang/hang/P2/3/0" '((0 . "TEXT") (8 . "KT-HOAN-THIEN") (7 . "VN_ARIAL") (10 21700.0 9700.0 0.0) (11 21700.0 9700.0 0.0) (40 . 200.0) (1 . "L\U+00E1t g\U+1EA1ch granite") (50 . 0.0) (72 . 0) (73 . 2) (-3 ("23HG_CAD" (1000 . "09/hoan_thien/bang/hang/P2/3/0") (1000 . "09")))))
  (hg23:em "09/hoan_thien/bang/hang/P2/3/1" '((0 . "TEXT") (8 . "KT-HOAN-THIEN") (7 . "VN_ARIAL") (10 21700.0 9400.0 0.0) (11 21700.0 9400.0 0.0) (40 . 200.0) (1 . "600\U+00D7600") (50 . 0.0) (72 . 0) (73 . 2) (-3 ("23HG_CAD" (1000 . "09/hoan_thien/bang/hang/P2/3/1") (1000 . "09")))))
  (hg23:em "09/hoan_thien/bang/hang/P2/4/0" '((0 . "TEXT") (8 . "KT-HOAN-THIEN") (7 . "VN_ARIAL") (10 25300.0 9700.0 0.0) (11 25300.0 9700.0 0.0) (40 . 200.0) (1 . "\U+1ED0p g\U+1EA1ch men cao") (50 . 0.0) (72 . 0) (73 . 2) (-3 ("23HG_CAD" (1000 . "09/hoan_thien/bang/hang/P2/4/0") (1000 . "09")))))
  (hg23:em "09/hoan_thien/bang/hang/P2/4/1" '((0 . "TEXT") (8 . "KT-HOAN-THIEN") (7 . "VN_ARIAL") (10 25300.0 9400.0 0.0) (11 25300.0 9400.0 0.0) (40 . 200.0) (1 . "1,5 m") (50 . 0.0) (72 . 0) (73 . 2) (-3 ("23HG_CAD" (1000 . "09/hoan_thien/bang/hang/P2/4/1") (1000 . "09")))))
  (hg23:em "09/hoan_thien/bang/hang/P2/5/0" '((0 . "TEXT") (8 . "KT-HOAN-THIEN") (7 . "VN_ARIAL") (10 28500.0 9550.0 0.0) (11 28500.0 9550.0 0.0) (40 . 200.0) (1 . "Tr\U+1EA7n th\U+1EA1ch cao") (50 . 0.0) (72 . 0) (73 . 2) (-3 ("23HG_CAD" (1000 . "09/hoan_thien/bang/hang/P2/5/0") (1000 . "09")))))
  (hg23:em "09/hoan_thien/bang/hang/P2/6/0" '((0 . "TEXT") (8 . "KT-HOAN-THIEN") (7 . "VN_ARIAL") (10 31700.0 9550.0 0.0) (11 31700.0 9550.0 0.0) (40 . 200.0) (1 . "\U+00B10.000") (50 . 0.0) (72 . 1) (73 . 2) (-3 ("23HG_CAD" (1000 . "09/hoan_thien/bang/hang/P2/6/0") (1000 . "09")))))
  (hg23:em "09/hoan_thien/bang/hang/P3/0/0" '((0 . "TEXT") (8 . "KT-HOAN-THIEN") (7 . "VN_ARIAL") (10 17200.0 8850.0 0.0) (11 17200.0 8850.0 0.0) (40 . 200.0) (1 . "3") (50 . 0.0) (72 . 1) (73 . 2) (-3 ("23HG_CAD" (1000 . "09/hoan_thien/bang/hang/P3/0/0") (1000 . "09")))))
  (hg23:em "09/hoan_thien/bang/hang/P3/1/0" '((0 . "TEXT") (8 . "KT-HOAN-THIEN") (7 . "VN_ARIAL") (10 17700.0 8850.0 0.0) (11 17700.0 8850.0 0.0) (40 . 200.0) (1 . "PH\U+00D2NG NG\U+1EE6") (50 . 0.0) (72 . 0) (73 . 2) (-3 ("23HG_CAD" (1000 . "09/hoan_thien/bang/hang/P3/1/0") (1000 . "09")))))
  (hg23:em "09/hoan_thien/bang/hang/P3/2/0" '((0 . "TEXT") (8 . "KT-HOAN-THIEN") (7 . "VN_ARIAL") (10 20800.0 8850.0 0.0) (11 20800.0 8850.0 0.0) (40 . 200.0) (1 . "15,12") (50 . 0.0) (72 . 1) (73 . 2) (-3 ("23HG_CAD" (1000 . "09/hoan_thien/bang/hang/P3/2/0") (1000 . "09")))))
  (hg23:em "09/hoan_thien/bang/hang/P3/3/0" '((0 . "TEXT") (8 . "KT-HOAN-THIEN") (7 . "VN_ARIAL") (10 21700.0 8850.0 0.0) (11 21700.0 8850.0 0.0) (40 . 200.0) (1 . "S\U+00E0n g\U+1ED7 c\U+00F4ng nghi\U+1EC7p") (50 . 0.0) (72 . 0) (73 . 2) (-3 ("23HG_CAD" (1000 . "09/hoan_thien/bang/hang/P3/3/0") (1000 . "09")))))
  (hg23:em "09/hoan_thien/bang/hang/P3/4/0" '((0 . "TEXT") (8 . "KT-HOAN-THIEN") (7 . "VN_ARIAL") (10 25300.0 8850.0 0.0) (11 25300.0 8850.0 0.0) (40 . 200.0) (1 . "S\U+01A1n n\U+01B0\U+1EDBc 1 l\U+00F3t 2 ph\U+1EE7") (50 . 0.0) (72 . 0) (73 . 2) (-3 ("23HG_CAD" (1000 . "09/hoan_thien/bang/hang/P3/4/0") (1000 . "09")))))
  (hg23:em "09/hoan_thien/bang/hang/P3/5/0" '((0 . "TEXT") (8 . "KT-HOAN-THIEN") (7 . "VN_ARIAL") (10 28500.0 8850.0 0.0) (11 28500.0 8850.0 0.0) (40 . 200.0) (1 . "Tr\U+1EA7n th\U+1EA1ch cao") (50 . 0.0) (72 . 0) (73 . 2) (-3 ("23HG_CAD" (1000 . "09/hoan_thien/bang/hang/P3/5/0") (1000 . "09")))))
  (hg23:em "09/hoan_thien/bang/hang/P3/6/0" '((0 . "TEXT") (8 . "KT-HOAN-THIEN") (7 . "VN_ARIAL") (10 31700.0 8850.0 0.0) (11 31700.0 8850.0 0.0) (40 . 200.0) (1 . "\U+00B10.000") (50 . 0.0) (72 . 1) (73 . 2) (-3 ("23HG_CAD" (1000 . "09/hoan_thien/bang/hang/P3/6/0") (1000 . "09")))))
  (hg23:em "09/hoan_thien/bang/hang/P4/0/0" '((0 . "TEXT") (8 . "KT-HOAN-THIEN") (7 . "VN_ARIAL") (10 17200.0 8150.0 0.0) (11 17200.0 8150.0 0.0) (40 . 200.0) (1 . "4") (50 . 0.0) (72 . 1) (73 . 2) (-3 ("23HG_CAD" (1000 . "09/hoan_thien/bang/hang/P4/0/0") (1000 . "09")))))
  (hg23:em "09/hoan_thien/bang/hang/P4/1/0" '((0 . "TEXT") (8 . "KT-HOAN-THIEN") (7 . "VN_ARIAL") (10 17700.0 8150.0 0.0) (11 17700.0 8150.0 0.0) (40 . 200.0) (1 . "S\U+1EA2NH THANG") (50 . 0.0) (72 . 0) (73 . 2) (-3 ("23HG_CAD" (1000 . "09/hoan_thien/bang/hang/P4/1/0") (1000 . "09")))))
  (hg23:em "09/hoan_thien/bang/hang/P4/2/0" '((0 . "TEXT") (8 . "KT-HOAN-THIEN") (7 . "VN_ARIAL") (10 20800.0 8150.0 0.0) (11 20800.0 8150.0 0.0) (40 . 200.0) (1 . "15,12") (50 . 0.0) (72 . 1) (73 . 2) (-3 ("23HG_CAD" (1000 . "09/hoan_thien/bang/hang/P4/2/0") (1000 . "09")))))
  (hg23:em "09/hoan_thien/bang/hang/P4/3/0" '((0 . "TEXT") (8 . "KT-HOAN-THIEN") (7 . "VN_ARIAL") (10 21700.0 8300.0 0.0) (11 21700.0 8300.0 0.0) (40 . 200.0) (1 . "L\U+00E1t g\U+1EA1ch granite") (50 . 0.0) (72 . 0) (73 . 2) (-3 ("23HG_CAD" (1000 . "09/hoan_thien/bang/hang/P4/3/0") (1000 . "09")))))
  (hg23:em "09/hoan_thien/bang/hang/P4/3/1" '((0 . "TEXT") (8 . "KT-HOAN-THIEN") (7 . "VN_ARIAL") (10 21700.0 8000.0 0.0) (11 21700.0 8000.0 0.0) (40 . 200.0) (1 . "600\U+00D7600") (50 . 0.0) (72 . 0) (73 . 2) (-3 ("23HG_CAD" (1000 . "09/hoan_thien/bang/hang/P4/3/1") (1000 . "09")))))
  (hg23:em "09/hoan_thien/bang/hang/P4/4/0" '((0 . "TEXT") (8 . "KT-HOAN-THIEN") (7 . "VN_ARIAL") (10 25300.0 8150.0 0.0) (11 25300.0 8150.0 0.0) (40 . 200.0) (1 . "S\U+01A1n n\U+01B0\U+1EDBc 1 l\U+00F3t 2 ph\U+1EE7") (50 . 0.0) (72 . 0) (73 . 2) (-3 ("23HG_CAD" (1000 . "09/hoan_thien/bang/hang/P4/4/0") (1000 . "09")))))
  (hg23:em "09/hoan_thien/bang/hang/P4/5/0" '((0 . "TEXT") (8 . "KT-HOAN-THIEN") (7 . "VN_ARIAL") (10 28500.0 8150.0 0.0) (11 28500.0 8150.0 0.0) (40 . 200.0) (1 . "Tr\U+00E1t tr\U+1EA7n, s\U+01A1n") (50 . 0.0) (72 . 0) (73 . 2) (-3 ("23HG_CAD" (1000 . "09/hoan_thien/bang/hang/P4/5/0") (1000 . "09")))))
  (hg23:em "09/hoan_thien/bang/hang/P4/6/0" '((0 . "TEXT") (8 . "KT-HOAN-THIEN") (7 . "VN_ARIAL") (10 31700.0 8150.0 0.0) (11 31700.0 8150.0 0.0) (40 . 200.0) (1 . "\U+00B10.000") (50 . 0.0) (72 . 1) (73 . 2) (-3 ("23HG_CAD" (1000 . "09/hoan_thien/bang/hang/P4/6/0") (1000 . "09")))))
  (hg23:em "09/hoan_thien/bang/hang/P5/0/0" '((0 . "TEXT") (8 . "KT-HOAN-THIEN") (7 . "VN_ARIAL") (10 17200.0 7350.0 0.0) (11 17200.0 7350.0 0.0) (40 . 200.0) (1 . "5") (50 . 0.0) (72 . 1) (73 . 2) (-3 ("23HG_CAD" (1000 . "09/hoan_thien/bang/hang/P5/0/0") (1000 . "09")))))
  (hg23:em "09/hoan_thien/bang/hang/P5/1/0" '((0 . "TEXT") (8 . "KT-HOAN-THIEN") (7 . "VN_ARIAL") (10 17700.0 7350.0 0.0) (11 17700.0 7350.0 0.0) (40 . 200.0) (1 . "WC") (50 . 0.0) (72 . 0) (73 . 2) (-3 ("23HG_CAD" (1000 . "09/hoan_thien/bang/hang/P5/1/0") (1000 . "09")))))
  (hg23:em "09/hoan_thien/bang/hang/P5/2/0" '((0 . "TEXT") (8 . "KT-HOAN-THIEN") (7 . "VN_ARIAL") (10 20800.0 7350.0 0.0) (11 20800.0 7350.0 0.0) (40 . 200.0) (1 . "7,20") (50 . 0.0) (72 . 1) (73 . 2) (-3 ("23HG_CAD" (1000 . "09/hoan_thien/bang/hang/P5/2/0") (1000 . "09")))))
  (hg23:em "09/hoan_thien/bang/hang/P5/3/0" '((0 . "TEXT") (8 . "KT-HOAN-THIEN") (7 . "VN_ARIAL") (10 21700.0 7500.0 0.0) (11 21700.0 7500.0 0.0) (40 . 200.0) (1 . "L\U+00E1t g\U+1EA1ch ch\U+1ED1ng tr\U+01A1n") (50 . 0.0) (72 . 0) (73 . 2) (-3 ("23HG_CAD" (1000 . "09/hoan_thien/bang/hang/P5/3/0") (1000 . "09")))))
  (hg23:em "09/hoan_thien/bang/hang/P5/3/1" '((0 . "TEXT") (8 . "KT-HOAN-THIEN") (7 . "VN_ARIAL") (10 21700.0 7200.0 0.0) (11 21700.0 7200.0 0.0) (40 . 200.0) (1 . "300\U+00D7300") (50 . 0.0) (72 . 0) (73 . 2) (-3 ("23HG_CAD" (1000 . "09/hoan_thien/bang/hang/P5/3/1") (1000 . "09")))))
  (hg23:em "09/hoan_thien/bang/hang/P5/4/0" '((0 . "TEXT") (8 . "KT-HOAN-THIEN") (7 . "VN_ARIAL") (10 25300.0 7500.0 0.0) (11 25300.0 7500.0 0.0) (40 . 200.0) (1 . "\U+1ED0p g\U+1EA1ch men cao") (50 . 0.0) (72 . 0) (73 . 2) (-3 ("23HG_CAD" (1000 . "09/hoan_thien/bang/hang/P5/4/0") (1000 . "09")))))
  (hg23:em "09/hoan_thien/bang/hang/P5/4/1" '((0 . "TEXT") (8 . "KT-HOAN-THIEN") (7 . "VN_ARIAL") (10 25300.0 7200.0 0.0) (11 25300.0 7200.0 0.0) (40 . 200.0) (1 . "2,4 m") (50 . 0.0) (72 . 0) (73 . 2) (-3 ("23HG_CAD" (1000 . "09/hoan_thien/bang/hang/P5/4/1") (1000 . "09")))))
  (hg23:em "09/hoan_thien/bang/hang/P5/5/0" '((0 . "TEXT") (8 . "KT-HOAN-THIEN") (7 . "VN_ARIAL") (10 28500.0 7350.0 0.0) (11 28500.0 7350.0 0.0) (40 . 200.0) (1 . "Tr\U+1EA7n nh\U+1EF1a") (50 . 0.0) (72 . 0) (73 . 2) (-3 ("23HG_CAD" (1000 . "09/hoan_thien/bang/hang/P5/5/0") (1000 . "09")))))
  (princ))

(defun hg23:ve-3 ()
  (hg23:em "09/hoan_thien/bang/hang/P5/6/0" '((0 . "TEXT") (8 . "KT-HOAN-THIEN") (7 . "VN_ARIAL") (10 31700.0 7350.0 0.0) (11 31700.0 7350.0 0.0) (40 . 200.0) (1 . "-0.020") (50 . 0.0) (72 . 1) (73 . 2) (-3 ("23HG_CAD" (1000 . "09/hoan_thien/bang/hang/P5/6/0") (1000 . "09")))))
  (hg23:em "09/hoan_thien/bang/hang/P6/0/0" '((0 . "TEXT") (8 . "KT-HOAN-THIEN") (7 . "VN_ARIAL") (10 17200.0 6550.0 0.0) (11 17200.0 6550.0 0.0) (40 . 200.0) (1 . "6") (50 . 0.0) (72 . 1) (73 . 2) (-3 ("23HG_CAD" (1000 . "09/hoan_thien/bang/hang/P6/0/0") (1000 . "09")))))
  (hg23:em "09/hoan_thien/bang/hang/P6/1/0" '((0 . "TEXT") (8 . "KT-HOAN-THIEN") (7 . "VN_ARIAL") (10 17700.0 6550.0 0.0) (11 17700.0 6550.0 0.0) (40 . 200.0) (1 . "KHO") (50 . 0.0) (72 . 0) (73 . 2) (-3 ("23HG_CAD" (1000 . "09/hoan_thien/bang/hang/P6/1/0") (1000 . "09")))))
  (hg23:em "09/hoan_thien/bang/hang/P6/2/0" '((0 . "TEXT") (8 . "KT-HOAN-THIEN") (7 . "VN_ARIAL") (10 20800.0 6550.0 0.0) (11 20800.0 6550.0 0.0) (40 . 200.0) (1 . "7,92") (50 . 0.0) (72 . 1) (73 . 2) (-3 ("23HG_CAD" (1000 . "09/hoan_thien/bang/hang/P6/2/0") (1000 . "09")))))
  (hg23:em "09/hoan_thien/bang/hang/P6/3/0" '((0 . "TEXT") (8 . "KT-HOAN-THIEN") (7 . "VN_ARIAL") (10 21700.0 6700.0 0.0) (11 21700.0 6700.0 0.0) (40 . 200.0) (1 . "L\U+00E1t g\U+1EA1ch granite") (50 . 0.0) (72 . 0) (73 . 2) (-3 ("23HG_CAD" (1000 . "09/hoan_thien/bang/hang/P6/3/0") (1000 . "09")))))
  (hg23:em "09/hoan_thien/bang/hang/P6/3/1" '((0 . "TEXT") (8 . "KT-HOAN-THIEN") (7 . "VN_ARIAL") (10 21700.0 6400.0 0.0) (11 21700.0 6400.0 0.0) (40 . 200.0) (1 . "600\U+00D7600") (50 . 0.0) (72 . 0) (73 . 2) (-3 ("23HG_CAD" (1000 . "09/hoan_thien/bang/hang/P6/3/1") (1000 . "09")))))
  (hg23:em "09/hoan_thien/bang/hang/P6/4/0" '((0 . "TEXT") (8 . "KT-HOAN-THIEN") (7 . "VN_ARIAL") (10 25300.0 6550.0 0.0) (11 25300.0 6550.0 0.0) (40 . 200.0) (1 . "S\U+01A1n n\U+01B0\U+1EDBc 1 l\U+00F3t 2 ph\U+1EE7") (50 . 0.0) (72 . 0) (73 . 2) (-3 ("23HG_CAD" (1000 . "09/hoan_thien/bang/hang/P6/4/0") (1000 . "09")))))
  (hg23:em "09/hoan_thien/bang/hang/P6/5/0" '((0 . "TEXT") (8 . "KT-HOAN-THIEN") (7 . "VN_ARIAL") (10 28500.0 6550.0 0.0) (11 28500.0 6550.0 0.0) (40 . 200.0) (1 . "Tr\U+00E1t tr\U+1EA7n, s\U+01A1n") (50 . 0.0) (72 . 0) (73 . 2) (-3 ("23HG_CAD" (1000 . "09/hoan_thien/bang/hang/P6/5/0") (1000 . "09")))))
  (hg23:em "09/hoan_thien/bang/hang/P6/6/0" '((0 . "TEXT") (8 . "KT-HOAN-THIEN") (7 . "VN_ARIAL") (10 31700.0 6550.0 0.0) (11 31700.0 6550.0 0.0) (40 . 200.0) (1 . "\U+00B10.000") (50 . 0.0) (72 . 1) (73 . 2) (-3 ("23HG_CAD" (1000 . "09/hoan_thien/bang/hang/P6/6/0") (1000 . "09")))))
  (hg23:em "09/hoan_thien/bang/tong/0/0" '((0 . "TEXT") (8 . "KT-HOAN-THIEN") (7 . "VN_ARIAL") (10 16900.0 5850.0 0.0) (11 16900.0 5850.0 0.0) (40 . 200.0) (1 . "T\U+1ED5ng di\U+1EC7n t\U+00EDch") (50 . 0.0) (72 . 0) (73 . 2) (-3 ("23HG_CAD" (1000 . "09/hoan_thien/bang/tong/0/0") (1000 . "09")))))
  (hg23:em "09/hoan_thien/bang/tong/1/0" '((0 . "TEXT") (8 . "KT-HOAN-THIEN") (7 . "VN_ARIAL") (10 20800.0 5850.0 0.0) (11 20800.0 5850.0 0.0) (40 . 200.0) (1 . "90,72") (50 . 0.0) (72 . 1) (73 . 2) (-3 ("23HG_CAD" (1000 . "09/hoan_thien/bang/tong/1/0") (1000 . "09")))))
  (hg23:em "09/hoan_thien/bang/tong/2/0" '((0 . "TEXT") (8 . "KT-HOAN-THIEN") (7 . "VN_ARIAL") (10 21700.0 5850.0 0.0) (11 21700.0 5850.0 0.0) (40 . 200.0) (1 . "t\U+00EDnh 6/6 ph\U+00F2ng") (50 . 0.0) (72 . 0) (73 . 2) (-3 ("23HG_CAD" (1000 . "09/hoan_thien/bang/tong/2/0") (1000 . "09")))))
  (hg23:em "09/hoan_thien/bang/ghi_chu/0/0" '((0 . "TEXT") (8 . "KT-HOAN-THIEN") (7 . "VN_ARIAL") (10 16900.0 5300.0 0.0) (11 16900.0 5300.0 0.0) (40 . 200.0) (1 . "Ghi ch\U+00FA: di\U+1EC7n t\U+00EDch t\U+00EDnh theo \U+0111\U+01B0\U+1EDDng bao nh\U+1EADp; 6/6 ph\U+00F2ng c\U+00F3 \U+0111\U+01B0\U+1EDDng bao tr\U+00F9ng tim tr\U+1EE5c/tim t\U+01B0\U+1EDDng \U+2014 ch\U+01B0a") (50 . 0.0) (72 . 0) (73 . 2) (-3 ("23HG_CAD" (1000 . "09/hoan_thien/bang/ghi_chu/0/0") (1000 . "09")))))
  (hg23:em "09/hoan_thien/bang/ghi_chu/0/1" '((0 . "TEXT") (8 . "KT-HOAN-THIEN") (7 . "VN_ARIAL") (10 16900.0 5000.0 0.0) (11 16900.0 5000.0 0.0) (40 . 200.0) (1 . "tr\U+1EEB chi\U+1EC1u d\U+00E0y t\U+01B0\U+1EDDng, KH\U+00D4NG ph\U+1EA3i di\U+1EC7n t\U+00EDch th\U+00F4ng th\U+1EE7y.") (50 . 0.0) (72 . 0) (73 . 2) (-3 ("23HG_CAD" (1000 . "09/hoan_thien/bang/ghi_chu/0/1") (1000 . "09")))))
  (hg23:em "10/khung_ten/vien_giay" '((0 . "LWPOLYLINE") (100 . "AcDbEntity") (8 . "KT-KHUNG-TEN") (370 . 13) (100 . "AcDbPolyline") (90 . 4) (70 . 1) (10 -7900.0 -13400.0) (10 34100.0 -13400.0) (10 34100.0 16300.0) (10 -7900.0 16300.0) (-3 ("23HG_CAD" (1000 . "10/khung_ten/vien_giay") (1000 . "10")))))
  (hg23:em "10/khung_ten/khung_ve" '((0 . "LWPOLYLINE") (100 . "AcDbEntity") (8 . "KT-KHUNG-TEN") (370 . 50) (100 . "AcDbPolyline") (90 . 4) (70 . 1) (10 -5400.0 -12900.0) (10 33600.0 -12900.0) (10 33600.0 15800.0) (10 -5400.0 15800.0) (-3 ("23HG_CAD" (1000 . "10/khung_ten/khung_ve") (1000 . "10")))))
  (hg23:em "10/khung_ten/o/vien" '((0 . "LWPOLYLINE") (100 . "AcDbEntity") (8 . "KT-KHUNG-TEN") (370 . 50) (100 . "AcDbPolyline") (90 . 3) (70 . 0) (10 15600.0 -12900.0) (10 15600.0 -8900.0) (10 33600.0 -8900.0) (-3 ("23HG_CAD" (1000 . "10/khung_ten/o/vien") (1000 . "10")))))
  (hg23:em "10/khung_ten/o/ke/0" '((0 . "LINE") (8 . "KT-KHUNG-TEN") (370 . 18) (10 15600.0 -9700.0 0.0) (11 33600.0 -9700.0 0.0) (-3 ("23HG_CAD" (1000 . "10/khung_ten/o/ke/0") (1000 . "10")))))
  (hg23:em "10/khung_ten/o/ke/1" '((0 . "LINE") (8 . "KT-KHUNG-TEN") (370 . 18) (10 15600.0 -10500.0 0.0) (11 33600.0 -10500.0 0.0) (-3 ("23HG_CAD" (1000 . "10/khung_ten/o/ke/1") (1000 . "10")))))
  (hg23:em "10/khung_ten/o/ke/2" '((0 . "LINE") (8 . "KT-KHUNG-TEN") (370 . 18) (10 15600.0 -11100.0 0.0) (11 33600.0 -11100.0 0.0) (-3 ("23HG_CAD" (1000 . "10/khung_ten/o/ke/2") (1000 . "10")))))
  (hg23:em "10/khung_ten/o/ke/3" '((0 . "LINE") (8 . "KT-KHUNG-TEN") (370 . 18) (10 15600.0 -11700.0 0.0) (11 33600.0 -11700.0 0.0) (-3 ("23HG_CAD" (1000 . "10/khung_ten/o/ke/3") (1000 . "10")))))
  (hg23:em "10/khung_ten/o/ke/4" '((0 . "LINE") (8 . "KT-KHUNG-TEN") (370 . 18) (10 26600.0 -12300.0 0.0) (11 33600.0 -12300.0 0.0) (-3 ("23HG_CAD" (1000 . "10/khung_ten/o/ke/4") (1000 . "10")))))
  (hg23:em "10/khung_ten/o/ke/5" '((0 . "LINE") (8 . "KT-KHUNG-TEN") (370 . 18) (10 18000.0 -12900.0 0.0) (11 18000.0 -8900.0 0.0) (-3 ("23HG_CAD" (1000 . "10/khung_ten/o/ke/5") (1000 . "10")))))
  (hg23:em "10/khung_ten/o/ke/6" '((0 . "LINE") (8 . "KT-KHUNG-TEN") (370 . 18) (10 26600.0 -12900.0 0.0) (11 26600.0 -10500.0 0.0) (-3 ("23HG_CAD" (1000 . "10/khung_ten/o/ke/6") (1000 . "10")))))
  (hg23:em "10/khung_ten/o/ke/7" '((0 . "LINE") (8 . "KT-KHUNG-TEN") (370 . 18) (10 29000.0 -12900.0 0.0) (11 29000.0 -10500.0 0.0) (-3 ("23HG_CAD" (1000 . "10/khung_ten/o/ke/7") (1000 . "10")))))
  (hg23:em "10/khung_ten/nhan/du_an" '((0 . "TEXT") (8 . "KT-KHUNG-TEN") (7 . "VN_ARIAL") (10 15750.0 -9300.0 0.0) (11 15750.0 -9300.0 0.0) (40 . 200.0) (1 . "D\U+1EF0 \U+00C1N") (50 . 0.0) (72 . 0) (73 . 2) (-3 ("23HG_CAD" (1000 . "10/khung_ten/nhan/du_an") (1000 . "10")))))
  (hg23:em "10/khung_ten/gia_tri/du_an" '((0 . "TEXT") (8 . "KT-KHUNG-TEN") (7 . "VN_ARIAL") (10 18150.0 -9300.0 0.0) (11 18150.0 -9300.0 0.0) (40 . 350.0) (1 . "NH\U+00C0 \U+1EDE M\U+1EAAU (D\U+1EEE LI\U+1EC6U MINH HO\U+1EA0)") (50 . 0.0) (72 . 0) (73 . 2) (-3 ("23HG_CAD" (1000 . "10/khung_ten/gia_tri/du_an") (1000 . "10")))))
  (hg23:em "10/khung_ten/nhan/ban_ve" '((0 . "TEXT") (8 . "KT-KHUNG-TEN") (7 . "VN_ARIAL") (10 15750.0 -10100.0 0.0) (11 15750.0 -10100.0 0.0) (40 . 200.0) (1 . "B\U+1EA2N V\U+1EBC") (50 . 0.0) (72 . 0) (73 . 2) (-3 ("23HG_CAD" (1000 . "10/khung_ten/nhan/ban_ve") (1000 . "10")))))
  (hg23:em "10/khung_ten/gia_tri/ban_ve" '((0 . "TEXT") (8 . "KT-KHUNG-TEN") (7 . "VN_ARIAL") (10 18150.0 -10100.0 0.0) (11 18150.0 -10100.0 0.0) (40 . 350.0) (1 . "M\U+1EB6T B\U+1EB0NG T\U+1EA6NG 1") (50 . 0.0) (72 . 0) (73 . 2) (-3 ("23HG_CAD" (1000 . "10/khung_ten/gia_tri/ban_ve") (1000 . "10")))))
  (hg23:em "10/khung_ten/nhan/thiet_ke" '((0 . "TEXT") (8 . "KT-KHUNG-TEN") (7 . "VN_ARIAL") (10 15750.0 -10800.0 0.0) (11 15750.0 -10800.0 0.0) (40 . 200.0) (1 . "THI\U+1EBET K\U+1EBE") (50 . 0.0) (72 . 0) (73 . 2) (-3 ("23HG_CAD" (1000 . "10/khung_ten/nhan/thiet_ke") (1000 . "10")))))
  (hg23:em "10/khung_ten/nhan/so_hieu" '((0 . "TEXT") (8 . "KT-KHUNG-TEN") (7 . "VN_ARIAL") (10 26750.0 -10800.0 0.0) (11 26750.0 -10800.0 0.0) (40 . 200.0) (1 . "S\U+1ED0 HI\U+1EC6U") (50 . 0.0) (72 . 0) (73 . 2) (-3 ("23HG_CAD" (1000 . "10/khung_ten/nhan/so_hieu") (1000 . "10")))))
  (hg23:em "10/khung_ten/gia_tri/so_hieu" '((0 . "TEXT") (8 . "KT-KHUNG-TEN") (7 . "VN_ARIAL") (10 29150.0 -10800.0 0.0) (11 29150.0 -10800.0 0.0) (40 . 250.0) (1 . "KT-01") (50 . 0.0) (72 . 0) (73 . 2) (-3 ("23HG_CAD" (1000 . "10/khung_ten/gia_tri/so_hieu") (1000 . "10")))))
  (hg23:em "10/khung_ten/nhan/kiem_tra" '((0 . "TEXT") (8 . "KT-KHUNG-TEN") (7 . "VN_ARIAL") (10 15750.0 -11400.0 0.0) (11 15750.0 -11400.0 0.0) (40 . 200.0) (1 . "KI\U+1EC2M TRA") (50 . 0.0) (72 . 0) (73 . 2) (-3 ("23HG_CAD" (1000 . "10/khung_ten/nhan/kiem_tra") (1000 . "10")))))
  (hg23:em "10/khung_ten/nhan/ty_le" '((0 . "TEXT") (8 . "KT-KHUNG-TEN") (7 . "VN_ARIAL") (10 26750.0 -11400.0 0.0) (11 26750.0 -11400.0 0.0) (40 . 200.0) (1 . "T\U+1EF6 L\U+1EC6") (50 . 0.0) (72 . 0) (73 . 2) (-3 ("23HG_CAD" (1000 . "10/khung_ten/nhan/ty_le") (1000 . "10")))))
  (hg23:em "10/khung_ten/gia_tri/ty_le" '((0 . "TEXT") (8 . "KT-KHUNG-TEN") (7 . "VN_ARIAL") (10 29150.0 -11400.0 0.0) (11 29150.0 -11400.0 0.0) (40 . 250.0) (1 . "1:100") (50 . 0.0) (72 . 0) (73 . 2) (-3 ("23HG_CAD" (1000 . "10/khung_ten/gia_tri/ty_le") (1000 . "10")))))
  (hg23:em "10/khung_ten/nhan/trang_thai/0" '((0 . "TEXT") (8 . "KT-KHUNG-TEN") (7 . "VN_ARIAL") (10 15750.0 -12100.0 0.0) (11 15750.0 -12100.0 0.0) (40 . 200.0) (1 . "TR\U+1EA0NG TH\U+00C1I") (50 . 0.0) (72 . 0) (73 . 2) (-3 ("23HG_CAD" (1000 . "10/khung_ten/nhan/trang_thai/0") (1000 . "10")))))
  (hg23:em "10/khung_ten/nhan/trang_thai/1" '((0 . "TEXT") (8 . "KT-KHUNG-TEN") (7 . "VN_ARIAL") (10 15750.0 -12500.0 0.0) (11 15750.0 -12500.0 0.0) (40 . 200.0) (1 . "S\U+1ED0 LI\U+1EC6U") (50 . 0.0) (72 . 0) (73 . 2) (-3 ("23HG_CAD" (1000 . "10/khung_ten/nhan/trang_thai/1") (1000 . "10")))))
  (hg23:em "10/khung_ten/gia_tri/trang_thai" '((0 . "TEXT") (8 . "KT-KHUNG-TEN") (7 . "VN_ARIAL") (10 18150.0 -12300.0 0.0) (11 18150.0 -12300.0 0.0) (40 . 250.0) (1 . "CH\U+1EDC DUY\U+1EC6T") (50 . 0.0) (72 . 0) (73 . 2) (-3 ("23HG_CAD" (1000 . "10/khung_ten/gia_tri/trang_thai") (1000 . "10")))))
  (hg23:em "10/khung_ten/nhan/lan_sua" '((0 . "TEXT") (8 . "KT-KHUNG-TEN") (7 . "VN_ARIAL") (10 26750.0 -12000.0 0.0) (11 26750.0 -12000.0 0.0) (40 . 200.0) (1 . "L\U+1EA6N S\U+1EECA") (50 . 0.0) (72 . 0) (73 . 2) (-3 ("23HG_CAD" (1000 . "10/khung_ten/nhan/lan_sua") (1000 . "10")))))
  (hg23:em "10/khung_ten/gia_tri/lan_sua" '((0 . "TEXT") (8 . "KT-KHUNG-TEN") (7 . "VN_ARIAL") (10 29150.0 -12000.0 0.0) (11 29150.0 -12000.0 0.0) (40 . 250.0) (1 . "00") (50 . 0.0) (72 . 0) (73 . 2) (-3 ("23HG_CAD" (1000 . "10/khung_ten/gia_tri/lan_sua") (1000 . "10")))))
  (hg23:em "10/khung_ten/nhan/ngay" '((0 . "TEXT") (8 . "KT-KHUNG-TEN") (7 . "VN_ARIAL") (10 26750.0 -12600.0 0.0) (11 26750.0 -12600.0 0.0) (40 . 200.0) (1 . "NG\U+00C0Y") (50 . 0.0) (72 . 0) (73 . 2) (-3 ("23HG_CAD" (1000 . "10/khung_ten/nhan/ngay") (1000 . "10")))))
  (hg23:em "10/khung_ten/ten_ban_ve" '((0 . "TEXT") (8 . "KT-KHUNG-TEN") (7 . "VN_ARIAL") (10 14100.0 -5350.0 0.0) (11 14100.0 -5350.0 0.0) (40 . 500.0) (1 . "M\U+1EB6T B\U+1EB0NG T\U+1EA6NG 1") (50 . 0.0) (72 . 1) (73 . 2) (-3 ("23HG_CAD" (1000 . "10/khung_ten/ten_ban_ve") (1000 . "10")))))
  (hg23:em "10/khung_ten/ty_le" '((0 . "TEXT") (8 . "KT-KHUNG-TEN") (7 . "VN_ARIAL") (10 14100.0 -5950.0 0.0) (11 14100.0 -5950.0 0.0) (40 . 300.0) (1 . "T\U+1EF6 L\U+1EC6 1:100") (50 . 0.0) (72 . 1) (73 . 2) (-3 ("23HG_CAD" (1000 . "10/khung_ten/ty_le") (1000 . "10")))))
  (princ))

(defun C:23HG_VE (/ *error* cmde)
  (defun *error* (msg)
    (if cmde (setvar "CMDECHO" cmde))
    (hg23:xoa-tam)
    (if hg23:doc (vla-EndUndoMark hg23:doc))
    (if (and msg (not (wcmatch (strcase msg) "*CANCEL*,*QUIT*,*EXIT*")))
      (princ (strcat "\n23HG: dung giua chung - " msg)))
    (princ))
  (setq hg23:doc (vla-get-ActiveDocument (vlax-get-acad-object))
        hg23:ms (vla-get-ModelSpace hg23:doc)
        hg23:n 0 hg23:nloi 0 hg23:tmp nil)
  (vla-StartUndoMark hg23:doc)
  (setq cmde (getvar "CMDECHO"))
  (setvar "CMDECHO" 0)
  (regapp "23HG_CAD")
  (setvar "INSUNITS" 4)
  (setvar "MEASUREMENT" 1)
  (setvar "LTSCALE" 50.0)
  (hg23:bang)
  (hg23:ve-1)
  (hg23:ve-2)
  (hg23:ve-3)
  (setvar "CMDECHO" cmde)
  (vla-EndUndoMark hg23:doc)
  (princ (strcat "\n23HG: da tao " (itoa hg23:n) "/343 doi tuong, loi " (itoa hg23:nloi) "."))
  (princ))

(princ "\n23HG: da nap - go lenh 23HG_VE de ve.")
(princ)
